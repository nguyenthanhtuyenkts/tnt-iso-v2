;;; Generated by 1.WORK/TNT_Sync_Release14.ps1 - AutoCAD 2014 ASCII edition.
;;; ====================================================================================================
;;; TNT_PACKAGE_00_SYSTEM_ALL.lsp
;;; System helpers + global TNT settings only.
;;; This file intentionally does not load any other Lisp package.
;;; ====================================================================================================

(vl-load-com)
(setvar "MODEMACRO" "TNT Architecture")
(setvar "PICKFIRST" 1)

;;; ----------------------------------------------------------------------------------------------------
;;; Core system helpers
;;; ----------------------------------------------------------------------------------------------------
(defun TNT:SYS:LOG (msg /)
  (if (= (type msg) 'STR)
    (princ (strcat "\n[TNT] " msg))
  )
  (princ)
)

(defun TNT:SYS:STR? (x)
  (= (type x) 'STR)
)

(defun TNT:SYS:FILE? (p)
  (and (TNT:SYS:STR? p) (findfile p))
)

(defun TNT:SYS:DIR? (p)
  (and (TNT:SYS:STR? p) (vl-file-directory-p p))
)

(defun TNT:SYS:TRIM-SLASH (p)
  (if (TNT:SYS:STR? p)
    (vl-string-right-trim "\\/" p)
    ""
  )
)

(defun TNT:SYS:JOIN (base rel / b r)
  (setq b (TNT:SYS:TRIM-SLASH base)
        r rel)
  (cond
    ((not (and (TNT:SYS:STR? b) (TNT:SYS:STR? r))) nil)
    ((wcmatch r "*:\\*") r)
    (T (strcat b "\\" r))
  )
)

(setq *TNT.SYSTEM.FILE*
  (cond
    ((and (boundp '*load-truename*) (TNT:SYS:STR? *load-truename*)) *load-truename*)
    ((findfile "TNT_PACKAGE_00_SYSTEM_ALL.lsp"))
    (T nil)
  )
)

(setq *TNT.SYSTEM.ROOT*
  (if (TNT:SYS:STR? *TNT.SYSTEM.FILE*)
    (vl-filename-directory *TNT.SYSTEM.FILE*)
    "E:\\TNT\\0.TNT ISO\\00.TNT ISO 2026\\00_LISP"
  )
)

(setq *TNT.SYSTEM.OSMODE.NEAREST-BIT* 512)
(setq *TNT.SYSTEM.OSMODE.DEFAULT* 15871)
(setq *TNT.SYSTEM.ENABLE.COMMAND.REACTORS* nil)

(defun TNT:SYS:SAFE-SETVAR (var value / name val str)
  (cond
    ((and (listp var) (= (length var) 2)) (setq name (car var) val (cadr var)))
    (T (setq name var val value))
  )
  (setq str
    (cond
      ((= (type name) 'STR) name)
      ((= (type name) 'SYM) (vl-symbol-name name))
      (T nil)
    )
  )
  (if str
    (setvar str val)
    (TNT:SYS:LOG (strcat "SAFE-SETVAR invalid: " (vl-princ-to-string var)))
  )
  (princ)
)

(defun TNT:SYS:SAFE-GETVAR (var / name str)
  (setq name (if (and (listp var) (>= (length var) 1)) (car var) var))
  (setq str
    (cond
      ((= (type name) 'STR) name)
      ((= (type name) 'SYM) (vl-symbol-name name))
      (T nil)
    )
  )
  (if str
    (getvar str)
    (progn
      (TNT:SYS:LOG (strcat "SAFE-GETVAR invalid: " (vl-princ-to-string var)))
      nil
    )
  )
)

(defun TNT:SYS:PUSH (/ item)
  (setq *TNT.SYSTEM.SAVED*
    (mapcar
      '(lambda (item) (list item (TNT:SYS:SAFE-GETVAR item)))
      '("CMDECHO" "EXPERT" "FILEDIA" "ATTDIA" "ATTREQ" "CMDDIA" "PICKFIRST" "PICKADD" "DRAGMODE" "UCSFOLLOW" "MIRRTEXT")
    )
  )
  (foreach item
    '(("CMDECHO" 0) ("EXPERT" 0) ("FILEDIA" 1) ("ATTDIA" 1) ("ATTREQ" 1) ("CMDDIA" 1) ("PICKFIRST" 1) ("PICKADD" 2) ("DRAGMODE" 2) ("UCSFOLLOW" 0) ("MIRRTEXT" 0))
    (TNT:SYS:SAFE-SETVAR item nil)
  )
  (princ)
)

(defun TNT:SYS:POP (/ item)
  (if (and (boundp '*TNT.SYSTEM.SAVED*) *TNT.SYSTEM.SAVED*)
    (foreach item *TNT.SYSTEM.SAVED*
      (TNT:SYS:SAFE-SETVAR (car item) (cadr item))
    )
  )
  (setq *TNT.SYSTEM.SAVED* nil)
  (princ)
)

(defun TNT:SYS:RUN-SAFE (func / err oldcmdecho)
  (setq oldcmdecho (getvar "CMDECHO"))
  (TNT:SYS:PUSH)
  (setq err (vl-catch-all-apply func '()))
  (TNT:SYS:POP)
  (if oldcmdecho (setvar "CMDECHO" oldcmdecho))
  (if (vl-catch-all-error-p err)
    (TNT:SYS:LOG (strcat "ERROR: " (vl-catch-all-error-message err)))
  )
  (princ)
)

(defun TNT:SYSTEM:OSMODE-WITHOUT-NEAREST (value / v)
  (setq v (if (= (type value) 'INT) value (getvar "OSMODE")))
  v
)

(defun TNT:SYSTEM:ENSURE-OSMODE-NO-NEAREST (/)
  (princ)
)

(defun TNT:SYSTEM:CLEAN-OSMODE-RESET-REACTORS (/ grp obj reactions pair cb name hit)
  (foreach grp (vlr-reactors :vlr-editor-reactor)
    (foreach obj (cdr grp)
      (setq hit nil)
      (setq reactions (vl-catch-all-apply 'vlr-reactions (list obj)))
      (if (not (vl-catch-all-error-p reactions))
        (foreach pair reactions
          (setq cb (cdr pair))
          (setq name (strcase (vl-princ-to-string cb)))
          (if (member name '("RESETOSMODE" "TNT:MANAGE:RESET-OSMODE"))
            (setq hit T)
          )
        )
      )
      (if hit
        (vl-catch-all-apply 'vlr-remove (list obj))
      )
    )
  )
  (setq *TNT.MANAGE.OSMODE.REACTOR* nil)
  (princ)
)

(defun TNT:PACKAGE:FS:SAFE-PUT (fun args /)
  (vl-catch-all-apply (function (lambda () (apply fun args))))
)

(defun TNT:PACKAGE:FS:SAFE-CALL (fun args /)
  (vl-catch-all-apply (function (lambda () (apply fun args))))
)

(defun TNT:FS:SAFE-PUT (obj prop value / err)
  (if (and obj prop)
    (progn
      (setq err
        (vl-catch-all-apply
          (function (lambda () (vlax-put-property obj prop value)))
          '()
        )
      )
      (if (vl-catch-all-error-p err) nil obj)
    )
  )
)

(defun TNT:FS:SAFE-CALL (obj method args / err)
  (if (and obj method)
    (progn
      (setq err
        (vl-catch-all-apply
          (function (lambda () (apply method (cons obj args))))
          '()
        )
      )
      (if (vl-catch-all-error-p err) nil T)
    )
  )
)

(defun TNT:FS:STR-LOWER (s)
  (vl-string-translate "ABCDEFGHIJKLMNOPQRSTUVWXYZ" "abcdefghijklmnopqrstuvwxyz"
                       (vl-princ-to-string s))
)

(defun TNT:FS:EXT (s / p l)
  (setq l (TNT:FS:STR-LOWER (vl-princ-to-string s)))
  (if (and l (setq p (vl-string-search "." l (- (strlen l) 1))))
    (substr l (1+ p))
    ""
  )
)

(defun TNT:FS:WINFONTS-PATH (/ w)
  (setq w (getenv "WINDIR"))
  (if (and w (/= w "")) (strcat w "\\Fonts\\") "C:\\Windows\\Fonts\\")
)

(defun TNT:FS:FIND-FONTFILE (pfont / cand)
  (setq cand
    (vl-remove nil
      (list
        (findfile pfont)
        (findfile (strcat (getvar "ACADPREFIX") pfont))
        (findfile (strcat (TNT:FS:WINFONTS-PATH) pfont))
      )
    )
  )
  (if cand (car cand) pfont)
)

;;; ----------------------------------------------------------------------------------------------------
;;; Global TNT settings
;;; ----------------------------------------------------------------------------------------------------


;;; ====================================================================================================
;;; BEGIN SOURCE: B_TNT_Settings_Create_Layer.lsp
;;; ====================================================================================================
;;; ====================================================================================================
;;; *** B_TNT_SETTINGS_CREATE_LAYER.LSP ***
;;; ====================================================================================================
;;; * FILE    : B_TNT_SETTINGS_CREATE_LAYER.LSP
;;; * PURPOSE : 
;;;   - DATA LAYER HE THONG
;;; * QUY UOC DAT TEN:
;;;   - HAM/MO-DUN                             :  A:B:C
;;;   - BIEN TOAN CUC (CO CHU DICH)            :  *A.B.C*
;;;   - THAM SO HAM (TIEN TO P)                :  P*
;;;   - BIEN CUC BO (TIEN TO L, KHAI BAO SAU /):  / L*
;;;   - COMMAND (BAT DAU BANG C:)              :  C:A_B_C
;;; ====================================================================================================
;;; [0] APPLICATION / SIGNATURE
;;; ====================================================================================================
(VL-LOAD-COM)
(SETVAR "MODEMACRO" "TNT Architecture")
;;; ====================================================================================================
;;; [1] BANG DATE CHUAN (DUNG CHUNG)
;;; ====================================================================================================
;;; MEPF: MECHANICAL _ ELECTRICAL _ PLUMBING _ FIREFIGHTING 
;;; MECHANICAL (CO KHI)
;;; - HE THONG LIEN QUAN DEN HVAC LA HE THONG SUOI, THONG GIO VA DIEU HOA KHONG KHI
;;; - HE THONG THANG MAY, BOM NUOC, QUAT GIO, V.V.
;;; ELECTRICAL (DIEN)                 
;;; - HE THONG DIEN TRONG TOA NHA, TU CUNG CAP NGUON DIEN, PHAN PHOI DIEN, HE THONG CHIEU SANG
;;; - O CAM, DEN CAC HE THONG DIEU KHIEN VA TU DONG HOA, HE THONG NANG LUONG TAI TAO, V.V
;;; PLUMBING (CAP THOAT NUOC)
;;; - HE THONG CUNG CAP NUOC SACH, THOAT NUOC THAI, XU LY NUOC, HE THONG CAP NUOC NONG LANH, VA CAC HE THONG CAP THOAT NUOC KHAC
;;; FIREFIGHTING (PHONG CHAY CHUA CHAY)
;;; - HE THONG PHAT HIEN VA CHUA CHAY NHU BAO CHAY TU DONG, HE THONG SPRINKLER
;;; - HE THONG CHUA CHAY BANG BOT, KHI HOAC NUOC, CAC THIET BI CHUA CHAY CAM TAY, VA CAC BIEN PHAP PHONG CHONG CHAY NO
(DEFUN TNT:LAYER:STD-TABLE (/)
  '(
    ;; ARCHITECT
    ("....00________________________________" "N"   "250"   "CONTINUOUS"      "0"       "0"   "________________________________")
    ("....01_TNT_A_DRAWING"                   "P"   "7"     "CONTINUOUS"      "0"       "0"   "NET KHUNG BAN VE"                )
    ("....02_TNT_A_VIRTURAL"                  "P"   "9"     "CONTINUOUS"      "0.3"     "50"  "NET THAY"                        )
    ("....03_TNT_A_THIN"                      "P"   "251"   "CONTINUOUS"      "0.15"    "50"  "NET MANH"                        )    
    ("....04_TNT_A_HIDDEN"                    "P"   "251"   "HIDDEN"          "0"       "50"  "NET KHUAT"                       )
    ("....05_TNT_A_SECTION"                   "P"   "30"    "CONTINUOUS"      "0"       "50"  "NET CAT"                         )
    ("....06_TNT_A_SECTION-LINE"              "P"   "6"     "ACAD_ISO07W100"  "0"       "0"   "NET TRUC CAT"                    )    
    ("....07_TNT_A_BASE"                      "P"   "177"   "CENTER"          "0"       "0"   "NET TRUC"                        )
    ("....08_TNT_A_DETAIL"                    "P"   "156"   "HIDDEN"          "0"       "50"  "NET CHI TIET"                    )
    ("....09_TNT_A_COMPLETE"                  "P"   "8"     "CONTINUOUS"      "0"       "50"  "NET HOAN THIEN"                  )
    ("....10_TNT_A_COTE"                      "P"   "14"    "CONTINUOUS"      "0"       "0"   "NET CAO DO"                      )
    ("....11_TNT_A_PLOT"                      "N"   "250"   "CONTINUOUS"      "0"       "0"   "NET IN"                          )
    ;; FURNITURE
    ("....12________________________________" "N"   "250"   "CONTINUOUS"      "0"       "50"  "________________________________")
    ("....12_TNT_F_FURNITURE"                 "P"   "27"    "CONTINUOUS"      "0"       "50"  "NET NOI THAT"                    )
    ("....13_TNT_F_TREE"                      "P"   "76"    "CONTINUOUS"      "0"       "50"  "NET CAY"                         )
    ("....14_TNT_F_GLASS"                     "P"   "147"   "CONTINUOUS"      "0"       "50"  "NET KINH"                        )    
    ("....15_TNT_F_DOOR"                      "P"   "33"    "CONTINUOUS"      "0"       "50"  "NET CUA"                         )    
    ;; STRUCTURE
    ("....16________________________________" "N"   "250"   "CONTINUOUS"      "0"       "0"   "________________________________")
    ("....16_TNT_S_CONCRETE"                  "P"   "7"     "CONTINUOUS"      "0"       "50"  "NET BTCT"                        )
    ("....17_TNT_S_WALL"                      "P"   "41"    "CONTINUOUS"      "0"       "50"  "NET TUONG"                       )
    ("....18_TNT_S_COLUMN"                    "P"   "9"     "CONTINUOUS"      "0"       "50"  "NET COT"                         )
    ;; ANNOTATE
    ("....19________________________________" "N"   "250"   "CONTINUOUS"      "0"       "0"   "________________________________")
    ("....20_TNT_N_TEXT"                      "P"   "9"     "CONTINUOUS"      "0"       "0"   "NET CHU"                         )
    ("....21_TNT_N_LEADER"                    "P"   "9"     "CONTINUOUS"      "0"       "0"   "NET GHI CHU"                     )
    ("....22_TNT_N_DIMENSION"                 "P"   "251"   "CONTINUOUS"      "0"       "0"   "NET KICH THUOC"                  )
    ("....23_TNT_N_HATCH"                     "P"   "250"   "CONTINUOUS"      "0"       "50"  "NET VAT LIEU"                    )
    ("....24_TNT_N_ANNOTATE"                  "P"   "14"    "CONTINUOUS"      "0"       "0"   "NET CHU THICH"                   )
    ;; MECHANICAL
    ("....25________________________________" "N"   "250"   "CONTINUOUS"      "0"       "0"   "________________________________")
    ("....25_TNT_M_NOTE"                      "P"   "1"     "CONTINUOUS"      "0"       "0"   "NET THIET BI DHKK"               )
    ("....26_TNT_M_TEXT"                      "P"   "4"     "CONTINUOUS"      "0"       "0"   "NET CHU DHKK"                    )
    ("....27_TNT_M_CONTROL"                   "P"   "5"     "HIDDEN"          "0"       "0"   "NET DIEU KHIEN DHKK"             )
    ("....28_TNT_M_COPPER-PIPE"               "P"   "3"     "CONTINUOUS"      "0"       "0"   "NET ONG DONG"                    )
    ("....29_TNT_M_CONDENSED-W"               "P"   "6"     "CONTINUOUS"      "0"       "0"   "NET NUOC NGUNG"                  )
    ("....30_TNT_M_RETURN-DUCT"               "P"   "6"     "CONTINUOUS"      "0"       "0"   "NET HOI DHKK"                    )
    ("....31_TNT_M_SUPPLY-DUCT"               "P"   "4"     "CONTINUOUS"      "0"       "0"   "NET CAP DHKK"                    )
    ;; ELECTRICAL
    ("....32________________________________" "N"   "250"   "CONTINUOUS"      "0"       "0"   "________________________________")
    ("....32_TNT_E_NOTE"                      "P"   "1"     "CONTINUOUS"      "0"       "0"   "NET THIET BI DIEN"               )
    ("....33_TNT_E_TEXT"                      "P"   "2"     "CONTINUOUS"      "0"       "0"   "NET CHU PHAN DIEN"               )
    ("....34_TNT_E_LINE"                      "P"   "4"     "CONTINUOUS"      "0"       "0"   "NET SDNL DIEN"                   )
    ("....35_TNT_E_WIRE"                      "P"   "6"     "DASHDOT"         "0"       "0"   "NET DAY DIEN"                    )
    ;; PLUMBING
    ("....36________________________________" "N"   "250"   "CONTINUOUS"      "0"       "0"   "________________________________")
    ("....36_TNT_P_NOTE"                      "P"   "11"    "CONTINUOUS"      "0"       "0"   "NET THIET BI NUOC"               )
    ("....37_TNT_P_TEXT"                      "P"   "3"     "CONTINUOUS"      "0"       "0"   "NET CHU NUOC"                    )
    ("....38_TNT_P_SUPPLY-TANK"               "P"   "4"     "HIDDEN"          "0"       "0"   "NET CAP TET"                     )
    ("....39_TNT_P_SUPPLY-COOL"               "P"   "4"     "CONTINUOUS"      "0"       "0"   "NET CAP LANH"                    )
    ("....40_TNT_P_SUPPLY-HOT"                "P"   "1"     "HIDDEN"          "0"       "0"   "NET CAP NONG"                    )
    ("....41_TNT_P_DRAIN-TOILET"              "P"   "4"     "HIDDEN"          "0"       "0"   "NET THOAT XI"                    )
    ("....42_TNT_P_DRAIN-RAIN"                "P"   "5"     "HIDDEN"          "0"       "0"   "NET THOAT MUA"                   )
    ("....43_TNT_P_DRAIN-WASH"                "P"   "6"     "HIDDEN"          "0"       "0"   "NET THOAT RUA"                   )
    ("....44_TNT_P_DRAIN-VENT"                "P"   "2"     "HIDDEN"          "0"       "0"   "NET THONG HOI"                   )
    ("....45________________________________" "N"   "250"   "CONTINUOUS"      "0"       "0"   "________________________________")
    ("....46_TNT_BASE_MEP"                    "P"   "250"   "CONTINUOUS"      ""        ""    "NET BASE CHO MEP"                )
    ;; FIREFIGHTING
  ))
(DEFUN TNT:LAYER:STD-NAMES (/)
  (MAPCAR 'CAR (TNT:LAYER:STD-TABLE)))
;;; ====================================================================================================
;;; [2] DANH SACH LAYER BI LOAI TRU KHOI CO CHE EP BYLAYER - TOOL 2
;;; ====================================================================================================
(DEFUN TNT:LAYER:STD-EXCLUDE-TABLE (/)
  '(
    ;("....20_TNT_N_TEXT"       )
    ;("....21_TNT_N_LEADER"     )
    ;("....22_TNT_N_DIMENSION"  )
    ("....23_TNT_N_HATCH"      )
    ;("....24_TNT_N_ANNOTATE"   ) 
  ))
(DEFUN TNT:LAYER:STD-EXCLUDE-NAMES (/)
  (MAPCAR 'CAR (TNT:LAYER:STD-EXCLUDE-TABLE)))
;;; ====================================================================================================
;;; [3] LOAI BO KHOANG TRANG DAU/CUOI
;;; ====================================================================================================
(DEFUN TNT:STR:TRIM (s / a b)
  (if (and s (/= s ""))
    (progn
      (setq a (vl-string-right-trim " " s))
      (setq b (vl-string-left-trim " " a))
      b)
    s))
;;; ====================================================================================================
;;; END SOURCE: B_TNT_Settings_Create_Layer.lsp
;;; ====================================================================================================


;;; ====================================================================================================
;;; BEGIN SOURCE: L_TNT_Function_Create_System.lsp
;;; ====================================================================================================
;;; ====================================================================================================
;;; ----------------------------------- L_TNT_FUNCTION_CREATE_SYSTEM -----------------------------------
;;; ====================================================================================================
;;; * FILE      : L_TNT_FUNCTION_CREATE_SYSTEM
;;; * PURPOSE : 
;;;   - 
;;;   - 
;;; * QUY UOC DAT TEN:
;;;   - HAM/MO-DUN                             :  A:B:C
;;;   - BIEN TOAN CUC (CO CHU DICH)            :  *A.B.C*
;;;   - THAM SO HAM (TIEN TO P)                :  P*
;;;   - BIEN CUC BO (TIEN TO L, KHAI BAO SAU /):  / L*
;;;   - COMMAND (BAT DAU BANG C:)              :  C:A_B_C
;;; * LUU Y:
;;; ====================================================================================================
;;; [0] APPLICATION / SIGNATURE
;;; ====================================================================================================
(vl-load-com)
(setvar "MODEMACRO" "TNT Architecture")
;;; ====================================================================================================
;;; [2] HAM TAO SYSTEM
;;; ====================================================================================================
(defun TNT_SYSTEM_CREATE ()
  (TNT:SYS:RUN-SAFE (function TNT:SYSTEM:CREATE_VARIABLES))
  (princ)
)

(defun TNT_SETTING (/)
  (TNT_SYSTEM_CREATE)
  (TNT:SYS:LOG "DONE: TNT_SETTING.")
  (princ)
)

(defun c:TNT_SETTING (/)
  (TNT_SETTING)
  (princ)
)

(defun TNT_INIT_ALL (/)
  (TNT_SETTING)
  (cond
    ((member "TNT:LAY:CREATE" (atoms-family 1))
      (TNT:SYS:RUN-SAFE (function TNT:LAY:CREATE)))
    (T
      (TNT:SYS:LOG "SKIP: TNT layer create is not loaded."))
  )
  (cond
    ((member "TNT:SHORTCUT:LAYER:INIT" (atoms-family 1))
      (TNT:SHORTCUT:LAYER:INIT))
    ((member "TNT_SHORTCUT" (atoms-family 1))
      (TNT_SHORTCUT))
    (T
      (TNT:SYS:LOG "SKIP: TNT_SHORTCUT is not loaded."))
  )
  (TNT:SYS:LOG "DONE: TNT_INIT_ALL.")
  (princ)
)

(defun c:0 (/)
  (TNT_INIT_ALL)
  (princ)
)
;;; ====================================================================================================
;;; [3] SETTING SYSTEM VARIABLES
;;; ====================================================================================================
(defun TNT:SYSTEM:CREATE_VARIABLES (/)
    (TNT:SYSTEM_SETTING "PICKFIRST" 1)
  ;1 GROUP INTERFACE
    (TNT:SYSTEM_SETTING "MODEMACRO" "TNT Architecture")
    (TNT:SYSTEM_SETTING "MENUBAR" 1)                        	   ;HIEN THI MENUBAR

    (TNT:SYSTEM_SETTING "STATUSBAR" 1)                           ;HIEN THI THANH CONG CU BEN DUOI GOC PHAI
    (TNT:SYSTEM_SETTING "LAYOUTTAB" 1)                           ;HIEN THI THANH TAB LAYOUT

    (TNT:SYSTEM_SETTING "CURSORSIZE" 100)                        ;TANG KICH THUOC CROSSHAIR CON TRO CHUOT
    (TNT:SYSTEM_SETTING "CURSORTYPE" 0)                          ;HIEN THI CHUOT HINH CHU THAP
    ;(TNT:SYSTEM_SETTING "APERTURE" 15)                          ;DO RONG O VUONG BAT DIEM
    ;(TNT:SYSTEM_SETTING "PICKBOX" 15)                           ;DO RONG O VUONG CHON DIEM
    ;(TNT:SYSTEM_SETTING "GRIPSIZE" 15)                          ;DO RONG O VUONG CHUC NANG
  ;2 GROUP LAYER & LINETYPE

    (if (not (and (boundp 'TNT:AEC:SKIP-DIMENSIONS) TNT:AEC:SKIP-DIMENSIONS))
      (progn
        (TNT:SYSTEM_SETTING "DIMASSOC" 1)                       ;NON-ASSOCIATIVE DIMENSION OBJECTS
        (TNT:SYSTEM:DISASSOCIATE_DIMENSIONS)
      )
    )
    (TNT:SYSTEM_SETTING "HPLAYER" "....23_TNT_N_HATCH")        ;LAYER "HATCH"


    (TNT:SYSTEM_SETTING "LTSCALE" 1)                             ;TY LE NET VE THONG NHAT
    (TNT:SYSTEM_SETTING "CELTYPE" "CONTINUOUS")                  ;KIEU NET MAC DINH KHI VE MOI  
  ;3 GROUP TEXT & DIMSTYLE

  ;4 GROUP LEADER & HATCH    
  ;5 GROUP ANNOTATION % PROPORTION
    (TNT:SYSTEM_SETTING "CANNOSCALE" "1:1")                      ;TY LE HIEN HANH CUA ANNOTATIVE SCALE
    (TNT:SYSTEM_SETTING "SELECTIONANNODISPLAY" 0)                ;TAT HIEN THI ANNOTATIVE
    (TNT:SYSTEM_SETTING "ANNOALLVISIBLE" 0)                      ;CHI HIEN THI ANNOTATIVE PHU HOP
    (TNT:SYSTEM_SETTING "ANNOAUTOSCALE" 0)                       ;KHONG TU THEM SCALE KHI CHINH VIEWPORT
  ;6 GROUP VIEWPORT & SPACE
    (TNT:SYSTEM_SETTING "MIRRTEXT" 0)                            ;CHU KHONG BI LAT NGUOC KHI MIRROR
    (TNT:SYSTEM_SETTING "MIRRHATCH" 0)                           ;HATCH KHONG BI LAT NGUOC KHI MIRROR
    (TNT:SYSTEM_SETTING "UCSICON" 0)                             ;TAT BIEU TUONG TRUC TOA DO
  ;7 GROUP BLOCK & XREF
    (TNT:SYSTEM_SETTING "INSUNITS" 4)                            ;SET MILIMETERS KHI CHEN KHOI
    (TNT:SYSTEM_SETTING "INSUNITSDEFSOURCE" 4)                   ;SET MILIMETERS KHI CHEN KHOI
    (TNT:SYSTEM_SETTING "INSUNITSDEFTARGET" 4)                   ;SET MILIMETERS KHI XUAT BAN VE
    (TNT:SYSTEM_SETTING "ATTDIA" 1)                              ;INSERT CO HOP THOAI NHAP THUOC TINH
    (TNT:SYSTEM_SETTING "ATTREQ" 1)                              ;BAT LOI NHAC HOAC HOP THOAI CHO CAC GIA TRI THUOC TINH, THEO CHI DINH CUA ATTDIA
  ;8 GROUP PRINTING
    (TNT:SYSTEM_SETTING "FILEDIA" 1)                             ;HIEN THI HOP THOAI TREN FILE MENU SAVE OPEN
  ;9 GROUP SAVE & SYSTEM
    (TNT:SYSTEM_SETTING "ISAVEBAK" 1)                            ;TAO FILE BACKUP KHI SAVE
    (TNT:SYSTEM_SETTING "SAVETIME" 30)                           ;TU DONG SAVE FILE 30 PHUT
  ;10 SELECT & DISPLAY
    (TNT:SYSTEM:ENSURE_NAVVCUBE_OFF)

    (TNT:SYSTEM_SETTING "TRANSPARENCYDISPLAY" 0)                 ;LAYER KHONG BI MO
    (TNT:SYSTEM_SETTING "SELECTIONPREVIEW" 0)                    ;TAT HIGHT KHI DI CHUOT VAO DOI TUONG
    (TNT:SYSTEM_SETTING "HIGHLIGHT" 1)                           ;BAT HIGHT KHI CHON DOI TUONG
    (TNT:SYSTEM_SETTING "SELECTIONOFFSCREEN" 1)                  ;GIU DOI TUONG DUOC CHON KHI NAM NGOAI MAN HINH
    (TNT:SYSTEM:LOG-VARIABLE "SELECTIONOFFSCREEN")
  ;11 DRAW
    (TNT:SYSTEM_SETTING "SNAPMODE" 0)                            ;TAT BAT DIEM GRID
    (TNT:SYSTEM_SETTING "GRIDMODE" 0)                            ;TAT BAT DIEM GRID 
    (TNT:SYSTEM_SETTING "OSMODE" *TNT.SYSTEM.OSMODE.DEFAULT*)     ;BAT BAT DIEM, TRU NEAREST
    (TNT:SYSTEM_SETTING "APERTURE" 20)                           ;KHOANG CACH HIEN THI BAT DIEM
    (TNT:SYSTEM_SETTING "PEDITACCEPT" 1)                         ;TAO NHANH PLINE TU LINE KHONG HIEN THI HOP THOAI COMMAND
    (princ)
)
;;; ====================================================================================================
;;; [4] FUNCTION SYSTEM VARIABLES
;;; ====================================================================================================
(defun TNT:SYSTEM_SETTING ( PVAR PVAL / LERR LOLDVAL)
  (setq LERR
    (vl-catch-all-apply
      (function
        (lambda ()
          (setq LOLDVAL (getvar PVAR))
          (if (not (equal LOLDVAL PVAL))
            (progn
              (setvar PVAR PVAL)
              (princ (strcat "\n[TNT] DONE: CHANGE SYSTEM VARIABLE " PVAR " FROM " (vl-princ-to-string LOLDVAL) " -> " (vl-princ-to-string PVAL)))
            )
          )
        )
      )
      '()
    )
  )
  (if (vl-catch-all-error-p LERR)
    (TNT:SYS:LOG (strcat "SKIP SYSTEM VARIABLE " PVAR ": " (vl-catch-all-error-message LERR)))
  )
  (princ)
)

(defun TNT:SYSTEM:LOG-VARIABLE ( PVAR / LVAL)
  (setq LVAL (vl-catch-all-apply 'getvar (list PVAR)))
  (if (vl-catch-all-error-p LVAL)
    (TNT:SYS:LOG (strcat PVAR " = <UNAVAILABLE>: " (vl-catch-all-error-message LVAL)))
    (TNT:SYS:LOG (strcat PVAR " = " (vl-princ-to-string LVAL)))
  )
  (princ)
)

(defun TNT:SYSTEM:DISASSOCIATE_DIMENSIONS (/ LSS LOLD LERR)
  (setq LSS (ssget "_X" '((0 . "DIMENSION"))))
  (if LSS
    (progn
      (setq LOLD (getvar "CMDECHO"))
      (setvar "CMDECHO" 0)
      (setq LERR
        (vl-catch-all-apply
          '(lambda ()
             (vl-cmdf "_.DIMDISASSOCIATE" LSS "")
           )
        )
      )
      (setvar "CMDECHO" LOLD)
      (if (vl-catch-all-error-p LERR)
        (princ (strcat "\n[TNT] ERROR: DIMDISASSOCIATE FAILED: " (vl-catch-all-error-message LERR)))
        (princ (strcat "\n[TNT] DONE: DISASSOCIATE " (itoa (sslength LSS)) " DIMENSIONS."))
      )
    )
  )
  (princ)
)

(defun TNT:SYSTEM:ENSURE_NAVVCUBE_OFF ( / LERR LSPACE LOLD)
  (setq LSPACE (getvar "TILEMODE"))
  (if (= LSPACE 1)
    (progn
      (setq LOLD (getvar "CMDECHO"))
      (setvar "CMDECHO" 0)
      (setq LERR (vl-catch-all-apply 'vl-cmdf (list "_.NAVVCUBE" "_Off")))
      (setvar "CMDECHO" LOLD)
      (if (vl-catch-all-error-p LERR)
        (TNT:SYS:LOG (strcat "SKIP NAVVCUBE: " (vl-catch-all-error-message LERR)))
        (princ "\n[TNT] DONE: CHANGE SYSTEM NAVVCUBE OFF.")
      )
    )
    (princ "\n[TNT] DONE: CANCEL CHANGE SYSTEM NAVVCUBE LAYOUT.")
  )
)

(defun TNT:SYSTEM:NORMALIZE-COMMAND (CMD / NAME)
  (setq NAME (strcase (vl-princ-to-string CMD)))
  (while
    (and
      (> (strlen NAME) 0)
      (member (substr NAME 1 1) '("." "_" "-"))
    )
    (setq NAME (substr NAME 2))
  )
  NAME
)

(defun TNT:SYSTEM:COMMAND-NAME-FROM-DATA (DATA / RAW)
  (setq RAW
    (cond
      ((and (listp DATA) DATA) (car DATA))
      ((= (type DATA) 'STR) DATA)
      (T "")
    )
  )
  (TNT:SYSTEM:NORMALIZE-COMMAND RAW)
)

;;; ----------------------------------------------------------------------------------------------------
;;; STARTUP PALETTE SUPPRESS
;;; ----------------------------------------------------------------------------------------------------
(defun TNT:SYSTEM:STARTUP-PALETTE-COMMAND? (CMD / NAME)
  (setq NAME (TNT:SYSTEM:NORMALIZE-COMMAND CMD))
  (if
    (member
      NAME
      '(
        "TOOLPALETTES"
        "AECPROJECTPALETTESTARTUP"
        "PROJECTPALETTESTARTUP"
        "AECPROJECTNAVIGATORSTARTUP"
        "PROJECTNAVIGATORSTARTUP"
      )
    )
    T
    nil
  )
)

(defun TNT:SYSTEM:CLOSE-STARTUP-PALETTES (/ OLDCE)
  (setq OLDCE (getvar "CMDECHO"))
  (setvar "CMDECHO" 0)
  (vl-catch-all-apply 'vl-cmdf (list "_.TOOLPALETTESCLOSE"))
  (vl-catch-all-apply 'vl-cmdf (list "_.AECCLOSEPROJECTNAVIGATOR"))
  (vl-catch-all-apply 'vl-cmdf (list "_.CLOSEPROJECTNAVIGATOR"))
  (setvar "CMDECHO" OLDCE)
  (princ)
)

(defun TNT:SYSTEM:STARTUP-PALETTE-COMMAND-END (REACTOR DATA / CMD)
  (setq CMD (TNT:SYSTEM:COMMAND-NAME-FROM-DATA DATA))
  (if (TNT:SYSTEM:STARTUP-PALETTE-COMMAND? CMD)
    (vl-catch-all-apply 'TNT:SYSTEM:CLOSE-STARTUP-PALETTES nil)
  )
  (princ)
)

(defun TNT:SYSTEM:STARTUP-PALETTE-REACTOR-INIT (/)
  (if (and (boundp '*TNT.SYSTEM.STARTUP.PALETTE.REACTOR*) *TNT.SYSTEM.STARTUP.PALETTE.REACTOR*)
    (vl-catch-all-apply 'vlr-remove (list *TNT.SYSTEM.STARTUP.PALETTE.REACTOR*))
  )
  (setq *TNT.SYSTEM.STARTUP.PALETTE.REACTOR*
    (vlr-command-reactor
      nil
      '((:vlr-commandEnded . TNT:SYSTEM:STARTUP-PALETTE-COMMAND-END))
    )
  )
  (TNT:SYSTEM:CLOSE-STARTUP-PALETTES)
  (princ)
)

(defun TNT:SYSTEM:STARTUP-PALETTE-REACTOR-OFF (/)
  (if (and (boundp '*TNT.SYSTEM.STARTUP.PALETTE.REACTOR*) *TNT.SYSTEM.STARTUP.PALETTE.REACTOR*)
    (vl-catch-all-apply 'vlr-remove (list *TNT.SYSTEM.STARTUP.PALETTE.REACTOR*))
  )
  (setq *TNT.SYSTEM.STARTUP.PALETTE.REACTOR* nil)
  (princ)
)

(defun TNT:SYSTEM:COMMAND-REACTORS-INIT (/)
  (if *TNT.SYSTEM.ENABLE.COMMAND.REACTORS*
    (progn
      (vl-catch-all-apply 'TNT:SYSTEM:STARTUP-PALETTE-REACTOR-INIT nil)
    )
    (progn
      (TNT:SYSTEM:STARTUP-PALETTE-REACTOR-OFF)
    )
  )
  (princ)
)
;;; ====================================================================================================
;;; END SOURCE: L_TNT_Function_Create_System.lsp
;;; ====================================================================================================

;;; ----------------------------------------------------------------------------------------------------
;;; End
;;; ----------------------------------------------------------------------------------------------------
(TNT:SYSTEM:COMMAND-REACTORS-INIT)
(TNT:SYSTEM:CLEAN-OSMODE-RESET-REACTORS)
(TNT:SYS:LOG "TNT system settings loaded. No package autoload was executed.")
(princ)
