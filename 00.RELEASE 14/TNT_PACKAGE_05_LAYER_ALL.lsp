;;; Generated by 1.WORK/TNT_Sync_Release14.ps1 - AutoCAD 2014 ASCII edition.
;;; ====================================================================================================
;;; TNT_PACKAGE_05_LAYER_ALL.lsp
;;; Auto-generated consolidated package file. Source files are appended below in filename order.
;;; ====================================================================================================
(vl-load-com)
(setvar "MODEMACRO" "TNT Architecture")


;;; ====================================================================================================
;;; BEGIN SOURCE: B_TNT_Layer_Fix.lsp
;;; ====================================================================================================
;;; ====================================================================================================
;;; *** B_TNT_LAYER_FIX.LSP ***
;;; ====================================================================================================
;;; * FILE    : B_TNT_LAYER_FIX.LSP
;;; * PURPOSE : 
;;;   - EP 1 DOI TUONG VE BYLAYER NEU LAYER CUA NO THUOC DANH SACH CHUAN
;;; * QUY UOC DAT TEN:
;;;   - HAM/MO-DUN                             :  A:B:C
;;;   - BIEN TOAN CUC (CO CHU DICH)            :  *A.B.C*
;;;   - THAM SO HAM (TIEN TO P)                :  P*
;;;   - BIEN CUC BO (TIEN TO L, KHAI BAO SAU /):  / L*
;;;   - COMMAND (BAT DAU BANG C:)              :  C:A_B_C
;;; ====================================================================================================
;;; [0] APPLICATION / SIGNATURE
;;; ====================================================================================================
(vl-load-com)
(setvar "MODEMACRO" "TNT Architecture")
;;; ====================================================================================================
;;; [1] COMMAND / LENH NGUOI DUNG
;;; ====================================================================================================
(DEFUN c:TNT_LAYER (/)
  (TNT:SYS:RUN-SAFE (FUNCTION TNT:LAYER:RUN))
  (PRINC))
;;; ====================================================================================================
;;; [2] CHI EP BYLAYER CHO LAYER CHUAN
;;; ====================================================================================================
;; EP 1 DOI TUONG VE BYLAYER NEU LAYER CUA NO THUOC DANH SACH CHUAN
(DEFUN TNT:LAYER:SKIP-LTYPE-SYNC-P (LNAME / S)
  (SETQ S (STRCASE (TNT:STR:TRIM (VL-PRINC-TO-STRING LNAME))))
  (AND (BOUNDP '*TNT.LAYER.SKIP-LTYPE-SYNC-NAMES*)
       (MEMBER S *TNT.LAYER.SKIP-LTYPE-SYNC-NAMES*)))

(DEFUN TNT:ENT:SET-BYLAYER-IF-STD (OBJ PSET PEX / LNAME)
  (SETQ LNAME (STRCASE (TNT:STR:TRIM (VLA-GET-LAYER OBJ))))
  (IF (AND (MEMBER LNAME PSET) (NOT (MEMBER LNAME PEX)))
    (PROGN
      (TNT:PACKAGE:FS:SAFE-PUT 'VLA-PUT-COLOR       (LIST OBJ 256))
      (IF (AND (NOT (TNT:LAYER:SKIP-LTYPE-SYNC-P LNAME))
               (VLAX-PROPERTY-AVAILABLE-P OBJ 'LINETYPE))
        (TNT:PACKAGE:FS:SAFE-PUT 'VLA-PUT-LINETYPE  (LIST OBJ "BYLAYER")))
      (IF (VLAX-PROPERTY-AVAILABLE-P OBJ 'LINEWEIGHT)
        (TNT:PACKAGE:FS:SAFE-PUT 'VLA-PUT-LINEWEIGHT (LIST OBJ ACLNWTBYLAYER)))
      (IF (VLAX-PROPERTY-AVAILABLE-P OBJ 'PLOTSTYLENAME)
        (TNT:PACKAGE:FS:SAFE-PUT 'VLA-PUT-PLOTSTYLENAME (LIST OBJ "BYLAYER")))
      (IF (VLAX-PROPERTY-AVAILABLE-P OBJ 'TRANSPARENCY)
        (TNT:PACKAGE:FS:SAFE-PUT 'VLA-PUT-TRANSPARENCY (LIST OBJ 0)))
    ))
  (PRINC))

(DEFUN TNT:SPACE:FORCE-BYLAYER-STD (BTR PSET PEX / ENT)
  (if (and BTR (vlax-property-available-p BTR 'GetEntities))
    (VLAX-FOR ENT (vla-get-entities BTR) (TNT:ENT:SET-BYLAYER-IF-STD ENT PSET PEX))
    (VLAX-FOR ENT BTR (TNT:ENT:SET-BYLAYER-IF-STD ENT PSET PEX)))
  (PRINC))

(DEFUN TNT:MODEL:FORCE-BYLAYER-STD (/ DOC MS PSET PEX)
  (SETQ DOC  (VLA-GET-ACTIVEDOCUMENT (VLAX-GET-ACAD-OBJECT)))
  (SETQ MS   (VLA-GET-MODELSPACE DOC))
  (SETQ PSET (MAPCAR '(lambda (n) (strcase (TNT:STR:TRIM n))) (TNT:LAYER:STD-NAMES)))
  (SETQ PEX  (MAPCAR '(lambda (n) (strcase (TNT:STR:TRIM n))) (TNT:LAYER:STD-EXCLUDE-NAMES)))
  (TNT:SPACE:FORCE-BYLAYER-STD MS PSET PEX)
  (PRINC))

(DEFUN TNT:PAPER:FORCE-BYLAYER-STD (/ DOC LAYS LYT BTR PSET PEX)
  (SETQ DOC  (VLA-GET-ACTIVEDOCUMENT (VLAX-GET-ACAD-OBJECT)))
  (SETQ LAYS (VLA-GET-LAYOUTS DOC))
  (SETQ PSET (MAPCAR '(lambda (n) (strcase (TNT:STR:TRIM n))) (TNT:LAYER:STD-NAMES)))
  (SETQ PEX  (MAPCAR '(lambda (n) (strcase (TNT:STR:TRIM n))) (TNT:LAYER:STD-EXCLUDE-NAMES)))
  (VLAX-FOR LYT LAYS
    (IF (/= (STRCASE (VLA-GET-NAME LYT)) "MODEL")
      (PROGN
        (SETQ BTR (VLA-GET-BLOCK LYT))
        (TNT:SPACE:FORCE-BYLAYER-STD BTR PSET PEX))))
  (PRINC))
;;; ====================================================================================================
;;; [3] HAM CON
;;; ====================================================================================================
;; 1) EP BYLAYER CHO CAC DOI TUONG THUOC LAYER CHUAN
(DEFUN TNT:LAYER:FIX (/)
  (TNT:SYS:RUN-SAFE (FUNCTION (LAMBDA (/) (TNT:MODEL:FORCE-BYLAYER-STD))))
  (TNT:SYS:RUN-SAFE (FUNCTION (LAMBDA (/) (TNT:PAPER:FORCE-BYLAYER-STD))))
  (PRINC))
;; 2) TAO/DONG BO LAYER CHUAN + EP BYLAYER TREN CAC LAYER CHUAN (MODEL + PAPER)
(DEFUN TNT:LAYER:SYNC (/)
  (TNT:SYS:RUN-SAFE
    (FUNCTION
      (LAMBDA (/)
        (TNT:LAY:CREATE)                 ; TAO/RESET CAC LAYER CHUAN
        (TNT:MODEL:FORCE-BYLAYER-STD)    ; EP DOI TUONG MODEL NEU LAYER ? CHUAN
        (TNT:PAPER:FORCE-BYLAYER-STD)    ; EP DOI TUONG PAPER NEU LAYER ? CHUAN
      )))
  (PRINC))
;;; ====================================================================================================
;;; END
;;; ====================================================================================================
;; 3) Dam bao cac layer TNT chuan ton tai sau PURGE/AUDIT
(DEFUN TNT:LAYER:ENSURE-STANDARD (/)
  (TNT:LAY:CREATE)
  (PRINC))

;; 4) Lenh tong hop: tao/reset layer, phan loai doi tuong, ep ByLayer
(DEFUN TNT:LAYER:RUN (/ OLD-SKIP LERR)
  (SETQ OLD-SKIP (IF (BOUNDP '*TNT.LAYER.SKIP-LTYPE-SYNC-NAMES*)
                   *TNT.LAYER.SKIP-LTYPE-SYNC-NAMES*
                   NIL))
  (SETQ *TNT.LAYER.SKIP-LTYPE-SYNC-NAMES*
        '("....21_TNT_N_LEADER" "....08_TNT_A_DETAIL"))
  (SETQ LERR
        (VL-CATCH-ALL-APPLY
          '(LAMBDA (/)
             (TNT:LAY:CREATE)
             (TNT:LAYER:CHANGE)
             (TNT:MODEL:FORCE-BYLAYER-STD))))
  (SETQ *TNT.LAYER.SKIP-LTYPE-SYNC-NAMES* OLD-SKIP)
  (IF (VL-CATCH-ALL-ERROR-P LERR)
    (PRINC (STRCAT "\n[TNT] ERROR: TNT_LAYER: " (VL-CATCH-ALL-ERROR-MESSAGE LERR)))
    (PRINC "\n[TNT] DONE: TNT_LAYER.")
  )
  (PRINC))
;;; ====================================================================================================
;;; END SOURCE: B_TNT_Layer_Fix.lsp
;;; ====================================================================================================

;;; ====================================================================================================
;;; BEGIN SOURCE: D_TNT_Layer_Change.lsp
;;; ====================================================================================================
;;; ====================================================================================================
;;; *** D_TNT_LAYER_CHANGE.LSP ***
;;; ====================================================================================================
;;; * FILE    :  D_TNT_LAYER_CHANGE.LSP
;;; * PURPOSE :
;;;   - CHANGE LAYER HATCH, TEXT, LEADER, DIM
;;; * QUY UOC DAT TEN:
;;;   - HAM/MO-DUN                             :  TNT:A:...
;;;   - BIEN TOAN CUC (CO CHU DICH)            :  *TNT.A.B...*
;;;   - THAM SO HAM (TIEN TO P)                :  P*...
;;;   - BIEN CUC BO (TIEN TO L, KHAI BAO SAU /):  / L*...
;;;   - COMMAND (BAT DAU BANG C:)              :  C:TNT_A_...
;;; * LUU Y:
;;; ====================================================================================================
;;; [0] APPLICATION / SIGNATURE
;;; ====================================================================================================
(vl-load-com)
(setvar "MODEMACRO" "TNT Architecture")
;;; ====================================================================================================
;;; [1] COMMAND / LENH NGUOI DUNG
;;; ====================================================================================================
;;; ====================================================================================================
;;; [1] HAM CON
;;; ====================================================================================================
(defun TNT:LAYER:CHANGE (/ OLDCE)
  (setq OLDCE (getvar "CMDECHO"))
  (setvar "CMDECHO" 0)
  (command-s "UNDO" "BE")
  (TNT:LAYER:CHANGE:TEXT)
  (TNT:LAYER:CHANGE:LEADER)
  (TNT:LAYER:CHANGE:DIMENSION)
  (TNT:LAYER:CHANGE:HATCH)
  (command-s "UNDO" "END")
  (setvar "CMDECHO" OLDCE)
  (princ))

(defun TNT:LAYER:CHANGE:TEXT (/ CNT)
  (setq CNT (ssget "X"
              '(
                (-4 . "<AND")
                  (-4 . "<OR")
                    (0 . "TEXT")
                    (0 . "MTEXT")
                  (-4 . "OR>")
                  (-4 . "<NOT")
                    (-4 . "<OR")
                      (8 . "Defpoints")
                      (8 . "....23_TNT_N_HATCH")
                      (8 . "....24_TNT_N_ANNOTATE")                
                      (8 . "....25_TNT_M_NOTE")
                      (8 . "....26_TNT_M_TEXT")
                      (8 . "....32_TNT_E_NOTE")
                      (8 . "....33_TNT_E_TEXT")
                      (8 . "....36_TNT_P_NOTE")
                      (8 . "....37_TNT_P_TEXT")
                    (-4 . "OR>")
                  (-4 . "NOT>")
                (-4 . "AND>")
              )
            )
  )
  (if CNT
    (command-s "_.change" CNT "" "P" "LA" "....20_TNT_N_TEXT" "")
    (command-s ".TEXTTOFRONT" "A")    
  )
(princ))

(defun TNT:LAYER:CHANGE:LEADER (/ CNL)
  (setq CNL (ssget "X"
              '(
                (-4 . "<AND")
                  (-4 . "<OR")
                    (0 . "LEADER")
                    (0 . "MULTILEADER")
                  (-4 . "OR>")
                  (-4 . "<NOT")
                    (-4 . "<OR")
                      (8 . "Defpoints")
                      (8 . "....23_TNT_N_HATCH")
                      (8 . "....24_TNT_N_ANNOTATE")                
                      (8 . "....25_TNT_M_NOTE")
                      (8 . "....26_TNT_M_TEXT")
                      (8 . "....32_TNT_E_NOTE")
                      (8 . "....33_TNT_E_TEXT")
                      (8 . "....36_TNT_P_NOTE")
                      (8 . "....37_TNT_P_TEXT")
                    (-4 . "OR>")
                  (-4 . "NOT>")
                (-4 . "AND>")
              )
            )
  )
  (if CNL
    (command-s "_.change" CNL "" "P" "LA" "....21_TNT_N_LEADER" "")
  )
(princ))

(defun TNT:LAYER:CHANGE:DIMENSION (/ CND)
  (setq CND (ssget "X" '((0 . "DIMENSION"))))
  (if CND
    (command-s "_.change" CND "" "P" "LA" "....22_TNT_N_DIMENSION" "")
  )
(princ))

(defun TNT:LAYER:CHANGE:HATCH (/ CNH)
  (setq CNH (ssget "X" '((0 . "HATCH"))))
  (if CNH
    (progn
      (command-s "_.change" CNH "" "P" "LA" "....23_TNT_N_HATCH" "")
      (command-s ".DRAWORDER" CNH "" "B")
    )
  )
(princ))
;;; ====================================================================================================
;;; END
;;; ====================================================================================================
;;; ====================================================================================================
;;; END SOURCE: D_TNT_Layer_Change.lsp
;;; ====================================================================================================

;;; ====================================================================================================
;;; DIMENSION SHORTCUTS
;;; ====================================================================================================
(defun c:D1 (/)
  (command ".DIMLFAC")
  (setvar "DIMASZ" 1.1)
  (princ)
)

(defun c:D2 (/)
  (command ".DIMSCALE")
  (setvar "DIMASZ" 1.1)
  (princ)
)

;;; ====================================================================================================
;;; MOVE SELECTED OBJECTS TO LAYER 0
;;; ====================================================================================================
(defun c:N0 (/ *error* oldcmdecho ss)
  (setq oldcmdecho (getvar "CMDECHO"))
  (defun *error* (msg)
    (setvar "CMDECHO" oldcmdecho)
    (if (and msg (not (wcmatch (strcase msg) "*CANCEL*,*QUIT*,*EXIT*")))
      (princ (strcat "\n[TNT] ERROR: N0: " msg))
    )
    (princ)
  )
  (setvar "CMDECHO" 0)
  (setq ss (ssget "_I"))
  (if (not ss)
    (setq ss (ssget))
  )
  (if ss
    (progn
      (command-s "_.CHANGE" ss "" "_Properties" "_LAyer" "0" "")
      (princ (strcat "\n[TNT] N0: Da chuyen " (itoa (sslength ss)) " doi tuong sang layer 0."))
    )
    (princ "\n[TNT] N0: Khong co doi tuong nao duoc chon.")
  )
  (setvar "CMDECHO" oldcmdecho)
  (princ)
)

(princ "\n[TNT] Loaded TNT_PACKAGE_05_LAYER_ALL.lsp")
(princ)
