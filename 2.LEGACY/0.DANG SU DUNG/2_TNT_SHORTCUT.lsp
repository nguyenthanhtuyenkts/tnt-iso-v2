;;; AUTOLISP TNT
;;; APPLOAD
;;; NO FIX
;;; GOI LENH TRONG COMMAND:
  ;; "-LENH": GOI LENH KHONG DUNG HOP THOAI
  ;; "_LENH": GOI LENH TIENG ANH ENGLISH
  ;; ".LENH": GOI LENH GOC NGUYEN THUY
  ;; "'ENH": GOI LENH KHI DANG DUNG LENH KHAC
  ;; "LENH": GOI LENH BINH THUONG TUY CAD
;;; SETTING BAN DAU
  ;; 1. CAI CAC BIEN HE THONG 
    (setvar "MODEMACRO" "TNT Architecture")
    (defun c:SETTING ()  
    (setvar "cursorsize" 100)                           ;CHINH SIZE CON TRO CHUOT
    (setvar "cursortype" 0)                             ;HIEN THI CURSOR
    (setvar "ISAVEBAK" 1)                               ;TAO FILE BACKUP KHI SAVE
    (setvar "SAVETIME" 15)                              ;TU DONG SAVE FILE 30 PHUT
    (setvar "INSUNITSDEFSOURCE" 4)                      ;SET MILIMETERS KHI CHEN KHOI
    (setvar "INSUNITSDEFTARGET" 4)                      ;SET MILIMETERS KHI XUAT BAN VE
    (setvar "OSOPTIONS" 1)                              ;CHO PHEP BAT DIEM VAO HATCH
    ;(setvar "APERTURE" 15)                             ;DO RONG O VUONG BAT DIEM
    ;(setvar "PICKBOX" 15)                              ;DO RONG O VUONG CHON DIEM
    ;(setvar "GRIPSIZE" 15)                             ;DO RONG O VUONG CHUC NANG
    (setvar "MIRRTEXT" 0)                               ;CHU KHONG BI LAT NGUOC KHI MIRROR
    (setvar "MIRRHATCH" 0)                              ;HATCH KHONG BI LAT NGUOC KHI MIRROR
    (setvar "OSMODE" 16383)                             ;BAT TAT CA BAT DIEM
    (setvar "CANNOSCALE" "1:1" )                        ;TY LE 1:1
    (setvar "LTSCALE" 1)                                ;LTS = 1
    (setvar "ANNOALLVISIBLE" 0 )
    (setvar "ANNOAUTOSCALE" 0 )
    (setvar "SELECTIONEFFECT" 10 )                      ; CHON DOI TUONG KO BI DANG LUOI  
    (setvar "TRANSPARENCYDISPLAY" 0 )
    (setvar "DIMLAYER" "...11_TNT_LINE_DIMENSION")         ;LAYER "DIMENTION"
    (setvar "HPLAYER" "...10_TNT_LINE_HATCH")              ;LAYER "HATCH"
    (setvar "TEXTLAYER" "...9_TNT_LINE_TEXT")              ;LAYER "TEXT"
    (princ)
    )
  ;; 2. TRA MA DXF CUA DOI TUONG
    (defun c:DXF (/ MA MA1 )
    (setq MA (car (entsel)))
    (setq MA1 (entget MA))
    (princ MA1)
    (princ))
;;; PHIM TAT TNT
 ;; 1.PHIM TAT LENH VE
    (defun c:SE1 ()
      (command "OSMODE" 16383)(princ))
    (defun c:ATT ()
      (command ".ATTIPEDIT")(princ))
    (defun c:wq ()
      (command ".WIPEOUT")(princ))
    (defun c:BB ()
      (command ".BOUNDARY")(princ))
 ;; 2.LENH COPY
    (defun c:C (/ A B)
      (setq A (ssget))
      (setq B (getpoint "\n SELECT POINT:"))
      (command "COPY" A "" "M" B )(princ))
    (defun c:CV (/ A B)
      (setq A (ssget))
      (setq B (getpoint "\n SELECT BASE POINT:"))
      (command ".COPYBASE" B A "")(princ))
    (defun c:CB ()        
        (command ".PASTEBLOCK")(princ))
  ;; 3.LENH CHINH SUA
    (defun c:BR (/ A B)
      (setq A (ssget))
      (setq B (getpoint "\n SELECT POINT:"))
      (command ".BREAK" A B B )(princ))
    ;(defun c:RE ()
    ;  (setvar "cmdecho" 0)
    ;  (command ".REGEN")
    ;  (command ".-XREF" "_RELOAD" "*" )
    ; (PRINC))
    ;(defun c:SEE ()
      ;(command "osmode" 959)(princ))
    (defun c:CC ()
      (command ".CIRCLE")(princ))
    (defun c:E1 ()
      (command ".EXTEND")(princ))
    (defun c:` ()
      (command ".LINE")(princ))
    (defun c:`` ()
      (command ".PLINE")(princ))
    (defun c:V ()
      (command ".MOVE")(princ))
    (defun c:Q ()
      (command ".MATCHPROP")(princ))
    (defun c:R ()
      (command ".RECTANG")(princ))
    (defun c:TT ()
      (command ".TRIM")(princ))
    (defun c:TT1 (/ ENAME PT1 etrim PT1 )      
      (command "UNDO" "BE")
      (setq ENAME (entsel)
            PT1 (getpoint))
        (if (cond (etrim)
            (T (load "extrim.lisp" "") etrim))
          (etrim (car ENAME) PT1)
        )
      (command "UNDO" "END")
      (princ)
      )
    (defun c:SF ()
      (command ".OFFSET")(princ))
    (defun c:FF ()
      (command ".MIRROR")(princ))
    (defun c:RT ()
      (command ".ROTATE")(princ))
    (defun c:RT1 (/ A B C)           
         (SETQ C (SSGET))
         (SETQ A 90 )
         (setq B (getpoint))
         (COMMAND ".ROTATE" C "" B 90)    
         (PRINC))
    (defun c:``` ()
      (command ".SPLINE")(princ))
    (defun c:REF ()
      (command "-REFEDIT" "O" "A" "Y")(princ))
    (defun c:REFC ()
      (command ".REFCLOSE" "S" "")(princ))
    (defun c:BE ()
      (command "-BEDIT")(princ))
    (defun c:BC ()
      (command "_BCLOSE" "")(princ))
    (defun c:XZ ()
      (command ".XLINE")(princ))
    (defun c:1` ()    
      (command ".XLINE" "V" )(princ))
    (defun c:2` ()
      (COMMAND ".XLINE" "H" )(princ))
    (defun c:F ()
      (command ".FILLET") (princ))
    (defun c:F1 ()
      (command ".AECFILLET") (princ))
    (defun c:DRF (/ A)
      (SETQ A (SSGET))
      (command ".DRAWORDER" A "" "F" ) (princ))
    (defun c:DRB (/ A)
      (SETQ A (SSGET))
      (command ".DRAWORDER" A "" "B" ) (princ))
    (defun c:xre ()
      (command "-XREF" "R" "*" ) (princ))
 ;; 4.PHIM TAT VE SELECT
    (defun c:SD ()
      (sssetfirst nil (ssget (list (cons 0 "DIMENSION"))))
      (princ))
    (defun c:SA ()
      (sssetfirst nil (ssget (list (cons 0 "LEADER"))))
      (princ))
    (defun c:SB ()
      (sssetfirst nil (ssget (list (cons 0 "INSERT"))))
      (princ))
    (defun c:ST ()
      (sssetfirst nil (ssget (list (cons 0 "*TEXT,LEADER"))))  
      (princ))
    (defun c:SHT ()
      (sssetfirst nil (ssget (list (cons 0 "HATCH"))))
      (princ))
    (defun c:SV ()
      (sssetfirst nil (ssget (list (cons 0 "VIEWPORT"))))
      (princ)) 
 ;; 5.PHIM TAT VE DIM
    (defun c:D ()
         (command ".DIMLINEAR")   
         (PRINC))
    (defun c:DA ()
         (command ".DIMALIGNED")
         (PRINC))
    (defun c:DN ()
         (command ".DIMANGULAR")
         (PRINC))
    (defun c:DG ()
         (command ".DIMRADIUS")
         (PRINC))
    (defun c:DC ()
         (command ".DIMCONTINUE")          
         (PRINC))
    (defun c:DB ()
         (command ".DIMBASELINE")          
         (PRINC))
    (defun c:DE ()        
         (command "DIMSETDELETE")  
         (PRINC))
    (defun c:DX (/ A)  
         (SETQ A (SSGET))  
         (command "DIMSETEXTEND" A "E" )  
         (PRINC))
    (defun c:D1 ()
         (command ".DIMLFAC")
         (PRINC))
    (defun c:D2 ()
         (command ".DIMSCALE")
         (PRINC)) 
    (defun c:D4 (/ A B)
         (setq C (getint))  
         (SETQ A (SSGET))
         (SETQ B (SSGET))
         (COMMAND ".DIMSPACE" A B "" C )
         (command ".DIMEDIT" "H" B "")  
         (PRINC))
    (defun c:D3 (/ B)
          (setvar "CMDECHO" 0)
          (setq ENAME (car (entsel )))
          (setq ENAMELIST (entget ENAME))
          (setq B (cdr (assoc 41 ENAMELIST)))
          (command "DIMSCALE" B )
          (setvar "CMDECHO" 1)
          (princ)
    )
    (defun c:DST ()
         (COMMAND ".dimstyle")
         (PRINC))
    (defun c:DV (/ D)
         (setvar "cmdecho" 0)
         (SETQ D (SSGET))    
         (command "DIM" "DIMLFAC" "V" D "exit")
         (setvar "CMDECHO" 1)
         (PRINC))  
 ;; 6.PHIM TAT VE LAYER
    (defun c:QQ ()
      (command ".LAYMCUR")
      (PRINC))
    (defun c:1 ()
      (setvar "CMDECHO" 0)
      (setvar "DIMLAYER" ".")    
      (command ".LAYISO")
      (setvar "CMDECHO" 1)
    (PRINC))
    (defun c:2 ()
    (command ".LAYOFF")
    (PRINC))
    (defun c:3 ()
      (setvar "CMDECHO" 0)
      (setvar "DIMLAYER" "11_TNT_LINE_DIMENSION" )
      (command "-LAYER" "ON" "*" "")
      (setvar "CMDECHO" 1)
      (PRINC))      
 ;; 7.PHIM TAT VE LAYOUT
    (defun c:V1 ()
      (command "_-vports" "_2" "V")
      (PRINC))
    (defun c:V2 ()
      (command "_-vports" "_2" "H")
      (PRINC))
    (defun c:V3 ()
      (command "_-vports" "_SI" )
      (PRINC))
    (defun c:C1 ( / TILE)
    (setq TILE (getvar "TILEMODE")) 
    (if (= TILE 0)
        (progn
            (setvar "TILEMODE" 1))      
        (progn
            (setvar "TILEMODE" 0))
    )
    (princ))
    (defun c:C3 ()
      (command ".MODEL")
      (PRINC))
    (defun c:C2 ()
      (command ".LAYOUT" "S" "" )
      (PRINC))
 ;; 8.PHIM TAT VE GROUP 
    (defun c:g1 ()
      (if (= (getvar "PICKSTYLE") 0)
          (setvar "PICKSTYLE" 1)
          (setvar "PICKSTYLE" 0)
      )
      (princ))
 ;; 9.PHIM TAT CHUNG
    (defun C:PU (/ )
        (setvar "CMDECHO" 0)
        (command "-PURGE" "ALL" "" "N" )
        (command "-PURGE" "R" "" "N" )
        (command ".AUDIT" "Y" )
          (setvar "CMDECHO" 1)
        (princ)
      )
