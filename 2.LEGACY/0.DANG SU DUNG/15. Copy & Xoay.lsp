;***************************************************************************************************************************
;***************************************************************************************************************************
;15) CX,      	Copy & Xoay.
;***************************************************************************************************************************
;***************************************************************************************************************************

(defun c:CX (/ A B C D)
  (setvar "CMDECHO" 0)
  (prompt "\nFor rotated copy")
  (ssget)
  (setq A (getpoint "\nBase point: "))
  (command "ID" A)
  (setq B (getpoint "\nNew point <Return> if same as Base point> "))
  (if (= B nil) (setq B A))
;  (setq D (/ (* (getangle B "\nRotation angle <0>: ") 180.0) pi))
  (command "COPY" "P" "" A A)
  (command "MOVE" "P" "" A B)
  (command "ROTATE" "P" "" B pause)
  (setvar "CMDECHO" 1)
)
