(defun C:DTM (/ pc dt tyle fo)
  (setvar "CMDECHO" 0)
  (if (= fname nil)
    (setq fname (getfiled "Chon tap tin luu so lieu" "//" "txt" 1))
  )
  (setq fo (open fname "a"))
  (princ "Cac dien tich da chon:" fo)
  (princ "\n" fo)
  (if (= tylen nil)
    (progn
      (setq tylen (getreal "\nTy le ban ve 1/<1000>:"))
      (if (= tylen nil)
	(setq tylen 1000.0)
      )
    )
  )
  (setq tyle (/ (* tylen tylen) 1000000.0))
  (setq pc (getpoint "\nChon diem giua:"))
  (while (/= pc nil)
    (command "layer" "n" "dientich" "c" "white" "dientich" "")
    (command "bpoly" pc "")
    (command "Area" "O" "L")
    (command "erase" "L" "")
    (setq dt (getvar "AREA"))
    (setq dt (* dt tyle))
    (setq dt (rtos dt 2 2))
    (command "layer" "s" "dientich" "")
    (setq dt (strcat dt " m2"))
    (command "text" "c" pc 2.3 0.0 dt)
    (princ dt fo)
    (princ " m2")
    (princ "\n" fo)
    (setq pc (getpoint "\nChon diem giua:"))
  )
  (close fo)
  (princ)
 (setvar "CMDECHO" 1)
)
