;;; ====================================================================================================
;;; ----------------------------------- G_010_USER_INTERFACE_DCL_CMD -----------------------------------
;;; ====================================================================================================
;;; * FILE    : G_010_USER_INTERFACE_DCL_CMD
;;; * PURPOSE : 
;;;   - 
;;;   - 
;;; * QUY ƯỚC ĐẶT TÊN:
;;;   - HÀM/MÔ-ĐUN                             :  A:B:C
;;;   - BIẾN TOÀN CỤC (CÓ CHỦ ĐÍCH)            :  *A.B.C*
;;;   - THAM SỐ HÀM (TIỀN TỐ P)                :  P*
;;;   - BIẾN CỤC BỘ (TIỀN TỐ L, KHAI BÁO SAU /):  / L*
;;;   - COMMAND (BẮT ĐẦU BẰNG C:)              :  C:A_B_C
;;; ====================================================================================================
;;; [0] APPLICATION / SIGNATURE
;;; ====================================================================================================
(vl-load-com)
(setvar "MODEMACRO" "010.α")
;;; ====================================================================================================
;;; [1] COMMANDS - CREATE
;;; ====================================================================================================
(defun c:TNT_DCL_CREATE (/)
  (010:DCL:SHOW:CREATE)
  (princ)
)
;;; ====================================================================================================
;;; [2] COMMANDS - TOOLS
;;; ====================================================================================================
(defun c:TNT_DCL_TOOLS (/)
  (010:DCL:SHOW:TOOLS)
  (princ)
)
