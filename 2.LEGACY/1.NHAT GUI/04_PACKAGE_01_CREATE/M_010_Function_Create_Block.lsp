;;; ====================================================================================================
;;; ------------------------------------ M_010_FUNCTION_CREATE_BLOCK -----------------------------------
;;; ====================================================================================================
;;; * FILE    : M_010_FUNCTION_CREATE_BLOCK
;;; * PURPOSE : 
;;;   - 
;;;   - 
;;; * QUY ƯỚC ĐẶT TÊN:
;;;   - HÀM/MÔ-ĐUN                             :  A:B:C
;;;   - BIẾN TOÀN CỤC (CÓ CHỦ ĐÍCH)            :  *A.B.C*
;;;   - THAM SỐ HÀM (TIỀN TỐ P)                :  P*
;;;   - BIẾN CỤC BỘ (TIỀN TỐ L, KHAI BÁO SAU /):  / L*
;;;   - COMMAND (BẮT ĐẦU BẰNG C:)              :  C:A_B_C
;;; ====================================================================================================
;;; [0] APPLICATION / SIGNATURE
;;; ====================================================================================================
(vl-load-com)
(setvar "MODEMACRO" "010.α")
;;; ====================================================================================================
;;; [2] HÀM TẠO BLOCK
;;; ====================================================================================================
(defun 010_BLOCK_CREATE (/)
  (010:SYS:RUN-SAFE (function 010:BLOCK:MAKE))    
  (princ)
)
;;; ====================================================================================================
;;; [3] ISO-BASIC
;;; ====================================================================================================
  (defun 010:BLOCK:MAKE (/ SCALE PT1 )    
    (setq SCALE 1
          PT1 '(0 0)
    )
    (command "-INSERT" "2025_ISO_TNT" PT1 SCALE SCALE 0
              "EXPLODE" "LAST"
    )
    (princ)
  )
