;;; ====================================================================================================
;;; ----------------------------- F_010_USER_INTERFACE_DCL_SHOW_DECORATION -----------------------------
;;; ====================================================================================================
;;; * FILE    : F_010_USER_INTERFACE_DCL_SHOW_DECORATION
;;; * PURPOSE : Gọi/Action hộp thoại:
;;;   - CREATE  : dialog
;;;   - ABOUT   : dialog
;;;   - HELP    : dialog
;;; * QUY ƯỚC ĐẶT TÊN:
;;;   - HÀM/MÔ-ĐUN                             :  A:B:C
;;;   - BIẾN TOÀN CỤC (CÓ CHỦ ĐÍCH)            :  *A.B.C*
;;;   - THAM SỐ HÀM (TIỀN TỐ P)                :  P*
;;;   - BIẾN CỤC BỘ (TIỀN TỐ L, KHAI BÁO SAU /):  / L*
;;;   - COMMAND (BẮT ĐẦU BẰNG C:)              :  C:A_B_C
;;; ====================================================================================================
;;; [0] APPLICATION / SIGNATURE
;;; ====================================================================================================
(vl-load-com)
(setvar "MODEMACRO" "010.α")
;;; ====================================================================================================
;;; [1] HÀM CON TẠO NÉT TRANG TRÍ HỘP THOẠI
;;; ====================================================================================================
(defun 010:DCL:SET_TILE_OF_SEP ( Tile / )
	(set_tile Tile "────────────────────────────────────────────────────────────────────────────────────")
	(mode_tile Tile 1)
)
(defun 010:DCL:SET_TILE_DECORATION ( NumTotal / Num Tile)
	(setq Num 0)
	(repeat NumTotal
		(setq Tile (strcat "sep" (itoa Num)))
		(set_tile Tile "──────────────────────────────────────────────────────────────────────────────────")
		(setq Num (+ Num 1))
	)
)
