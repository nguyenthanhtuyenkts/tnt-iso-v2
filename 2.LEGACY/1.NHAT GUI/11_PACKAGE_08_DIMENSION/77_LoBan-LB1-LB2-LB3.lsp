(defun c:LB1 ()
  (command "_.undo" "_begin")
  (setq ss (ssget '((0 . "DIMENSION"))))
  (if ss
    (progn
      (setq i 0)
      (repeat (sslength ss)
        (setq ent (ssname ss i))
        (setq entData (entget ent))
        (setq dimRealValue (cdr (assoc 42 entData)))
        (setq quotient (/ dimRealValue 261.0))
        (setq fraction (- quotient (fix quotient)))

        (if (or (and (>= fraction 0.0) (<= fraction 0.25))
                (and (>= fraction 0.75) (<= fraction 1.0)))
          (setq newText (strcat (rtos dimRealValue 2 0) " (tốt)"))
          (setq newText (strcat (rtos dimRealValue 2 0) " (xấu)"))
        )

        (setq oldText (cdr (assoc 1 entData)))
        (setq updatedText (strcat oldText " " newText))
        (setq entData (subst (cons 1 updatedText) (assoc 1 entData) entData))
        (entmod entData)
        (setq i (1+ i))
      )
      (command "REGEN")
    )
  )
  (command "_.undo" "_end")
  (princ)
)

(defun c:LB2 ()
  (command "_.undo" "_begin")
  (setq ss (ssget '((0 . "DIMENSION"))))
  (if ss
    (progn
      (setq i 0)
      (repeat (sslength ss)
        (setq ent (ssname ss i))
        (setq entData (entget ent))
        (setq dimRealValue (cdr (assoc 42 entData)))
        (setq quotient (/ dimRealValue 214.5))
        (setq fraction (- quotient (fix quotient)))

        (if (or (and (>= fraction 0.0) (<= fraction 0.25))
                (and (>= fraction 0.75) (<= fraction 1.0)))
          (setq newText (strcat (rtos dimRealValue 2 0) " (tốt)"))
          (setq newText (strcat (rtos dimRealValue 2 0) " (xấu)"))
        )

        (setq oldText (cdr (assoc 1 entData)))
        (setq updatedText (strcat oldText " " newText))
        (setq entData (subst (cons 1 updatedText) (assoc 1 entData) entData))
        (entmod entData)
        (setq i (1+ i))
      )
      (command "REGEN")
    )
  )
  (command "_.undo" "_end")
  (princ)
)

(defun c:LB3 ()
  (command "_.undo" "_begin")
  (setq ss (ssget '((0 . "DIMENSION"))))
  (if ss
    (progn
      (setq i 0)
      (repeat (sslength ss)
        (setq ent (ssname ss i))
        (setq entData (entget ent))
        (setq dimRealValue (cdr (assoc 42 entData)))
        (setq quotient (/ dimRealValue 194.0))
        (setq fraction (- quotient (fix quotient)))

        (if (or (and (>= fraction 0.0) (<= fraction 0.2))
                (and (>= fraction 0.4) (<= fraction 0.6))
                (and (>= fraction 0.8) (<= fraction 1.0)))
          (setq newText (strcat (rtos dimRealValue 2 0) " (tốt)"))
          (setq newText (strcat (rtos dimRealValue 2 0) " (xấu)"))
        )

        (setq oldText (cdr (assoc 1 entData)))
        (setq updatedText (strcat oldText " " newText))
        (setq entData (subst (cons 1 updatedText) (assoc 1 entData) entData))
        (entmod entData)
        (setq i (1+ i))
      )
      (command "REGEN")
    )
  )
  (command "_.undo" "_end")
  (princ)
)
