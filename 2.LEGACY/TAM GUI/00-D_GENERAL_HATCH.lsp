;;; I. PHAN HATCH
  ;; FIX BAT DIEM   
  ;; 1.PHIM TAT VE HATCH
    (defun c:H25 ()      
      (command "-HATCH" "CO" 250 "." "P" "S" )
      (PRINC))
    (defun c:H251 ()
      (command "-HATCH" "CO" 251 "." "P" "S" )
      (PRINC))
    (defun c:H252 ()
      (command "-HATCH" "CO" 252 "." "P" "S" )
      (PRINC))
    (defun c:H253 ()
      (command "-HATCH" "CO" 253 "." "P" "S" )
      (PRINC))
    (defun c:H254 ()
      (command "-HATCH" "CO" 254 "." "P" "S" )
      (PRINC))
    (defun c:H255 ()
      (command "-HATCH" "CO" 255 "." "P" "S" )
      (PRINC))  
    (defun c:HB (/ B)
      (SETQ B (SSGET))
      (command "-HATCHEDIT" B "DR" "B" )
      (PRINC))
    (defun c:HF (/ F)
      (SETQ F (SSGET))
      (command "-HATCHEDIT" F "DR" "F" )
      (PRINC))  
  ;; 2.SAO CHEP HATCH    
    (defun c:HC (/ OSM OLDERR 1error ENAME ELIST ETYPE OLD SOL PT1 LAYN )
      (setvar "MODEMACRO" "010 Architec")
      (command "UNDO" "BE")
      (setvar "CMDECHO" 0)      
      (setq ENAME (entsel "\nCHON HATCH")
            ELIST (entget (car ENAME ))
            ETYPE (cdr (assoc 0 ELIST))
            OLD (getvar "CLAYER")
      )
      (if (/= ETYPE "HATCH")
      (prompt "\nCHON LAI HATCH")
        (progn
          (setvar "OSMODE" 0)
          (setq SOL (setvar "HPNAME" (cdr (assoc 2 ELIST))))
          (if (/= SOL "SOLID")
            (progn
              (while (setq PT1 (getpoint "\nCHON POINT TRONG VUNG HATCH"))
                (setq LAYN (cdr (assoc 8 ELIST)))
                (setvar "HPNAME" (cdr (assoc 2 ELIST)))
                (setvar "HPSCALE" (cdr (assoc 41 ELIST)))
                (setvar "HPANG" (cdr (assoc 52 ELIST)))
                (setvar "HPCOLOR" "BYLAYER")                
                (setvar "CLAYER" LAYN )
                (command "BHATCH" PT1 "" )
                (setvar "CLAYER" OLD )
              )
            )
            (progn
              (while (setq PT1 (getpoint "\nCHON POINT TRONG VUNG HATCH"))
              (setq LAYN (cdr (assoc 8 ELIST)))
              (setvar "HPNAME" (cdr (assoc 2 ELIST)))
              (setvar "HPCOLOR" "BYLAYER")
              (setvar "CLAYER" LAYN )
              (command "BHATCH" PT1 "" )
              (setvar "CLAYER" OLD )
              )
            )
          )
        )
      )
      (setvar "OSMODE" 16383)
      (setvar "CMDECHO" 1)
      (command "UNDO" "END")
      (princ)
    )
  ;; 3.DI CHUYEN HATCH
    (defun c:HV (/ ENAME ELIST ETYPE OLD SOL LAYN PT1 )
      (setvar "MODEMACRO" "010 Architec")
      (setvar "CMDECHO" 0)
      (command "UNDO" "BE")      
      (setq ENAME (entsel "\nCHON HATCH")
            ELIST (entget (car ENAME))
            ETYPE (cdr (assoc 0 ELIST))
            OLD (getvar "CLAYER")        
      )
      (if (/= ETYPE "HATCH")
      (prompt "\nCHON LAI HATCH")
        (progn
          (setvar "OSMODE" 0)
          (setq SOL (setvar "HPNAME" (cdr (assoc 2 ELIST))))
          (if (/= SOL "SOLID")
            (progn
              (setq LAYN (cdr (assoc 8 ELIST)))
              (setvar "HPNAME" (cdr (assoc 2 ELIST)))
              (setvar "HPSCALE" (cdr (assoc 41 ELIST)))
              (setvar "HPANG" (cdr (assoc 52 ELIST)))
              (setq PT1 (getpoint "\nCHON POINT TRONG VUNG HATCH"))
              (setvar "CLAYER" LAYN )
              (entdel (car ENAME))
              (command "BHATCH" PT1 "" )
              (setvar "CLAYER" OLD )
            )
            (progn
              (setq LAYN (cdr (assoc 8 ELIST)))
              (setvar "HPNAME" (cdr (assoc 2 ELIST)))
              (setq PT1 (getpoint "\nCHON POINT TRONG VUNG HATCH"))
              (setvar "CLAYER" LAYN )
              (entdel (car ENAME))
              (command "BHATCH" PT1 "" )
              (setvar "CLAYER" OLD )
            )
          )
        )
      )
      (setvar "OSMODE" 16383)
      (setvar "CMDECHO" 1)
      (command "UNDO" "END")
      (princ)
    )
  ;; 4.THAY DOI TY LE HATCH
    (defun c:HS (/ ENAME ELIST ETYPE OSCL HSCL NSCL NLST)
      (setvar "MODEMACRO" "010 Architec")
      (setvar "CMDECHO" 0)
      (command "UNDO" "BE")
      (setq ENAME (entsel "\nCHON HATCH")
            ELIST (entget (car ENAME))
            ETYPE (cdr (assoc 0 ELIST))
            OSCL (assoc 41 ELIST)
      )
      (if (/= ETYPE "HATCH")
      (prompt "\nCHON LAI HATCH")
        (progn
          (setq HSCL (getreal (strcat "\nNHAP TY LE HATCH MOI: <" (rtos (cdr OSCL) 2) ">:"))
                NSCL (cons 41 HSCL)
                NLST (subst NSCL OSCL ELIST)
          )
          (entmod NLST)
          (command "HATCHEDIT" ENAME "" "" "" "")
        )
      )
      (command "UNDO" "END")
      (princ) 
    )
  ;; 5.THAY DOI GOC HATCH
    (defun c:HA (/ ENAME ELIST ETYPE OANG ANG NANG NLST)
      (setvar "MODEMACRO" "010 Architec")
      (setvar "CMDECHO" 0)
      (command "UNDO" "BE")
      (setq ENAME (entsel "\nCHON HATCH")
            ELIST (entget (car ENAME))
            ETYPE (cdr (assoc 0 ELIST))
            OANG (assoc 52 ELIST)
      )
      (if (/= ETYPE "HATCH")
      (prompt "\n CHON LAI HATCH")
        (progn
          (setq ANG (getangle (strcat "\nNHAP SO DO GOC HATCH MOI: <" (rtos (cdr OANG) 2) ">:"))
                NANG (cons 52 ANG)
                NLST (subst NANG OANG ELIST)
          )
          (entmod NLST)
          (command "HATCHEDIT" ENAME "" "" "" "")
        )
      )
      (command "UNDO" "END")
      (princ)
    )
  ;; 6.CHIA HATCH
    (defun c:HT (/ PLINE E HOBJ PT )
      (setvar "MODEMACRO" "010 Architec")
      (setvar "CMDECHO" 0)
      (command "UNDO" "BE")      
      (setq PLINE (car (entsel "\nCHON LINE"))
            E (entsel  "\nCHON HATCH" )
            HOBJ (car E)
            PT (cadr E)
      )
      (command "TRIM" PLINE "" PT "" "-HATCH" PT "" "MATCHPROP" HOBJ (entlast) "")
      (command "UNDO" "END")
      (princ)
    )
  ;; 7.THAY DOI ORIGIN HATCH    
    (defun c:HG (/ SS B SSL1 N ENAME ELIST ETYPE)
      (setvar "MODEMACRO" "010 Architec")
      (setvar "CMDECHO" 0)
      (command "UNDO" "BE")
      (setq SS (ssget))
      (setq B (getpoint)) 
      (setq SSL1 (sslength SS))
      (setq N 0)
        (while (< N SSL1)          
              (setq ENAME (ssname SS N)           
                    ELIST (entget ENAME)          
                    ETYPE (cdr (assoc 0 ELIST)))
              (cond
                ((= ETYPE "HATCH")
                (command "-HATCHEDIT" ENAME "O" "S" B "Y" )
                )
              )
            (setq N (+ N 1))
        )      
      (command "UNDO" "END")
      (setvar "CMDECHO" 1)
      (princ)
    )
  ;; 8. BAT TAT BAT DIEM HATCH
    (defun c:HSE ()
    (setvar "MODEMACRO" "010 Architec")
     (if (= (getvar "OSNAPHATCH") 0)
        (setvar "OSNAPHATCH" 1)
        (setvar "OSNAPHATCH" 0)
     )
    (princ))
  ;; 9. TAT ASSOCIATIVE
    (defun c:HSA (/ SS SSL1 N ENAME ELIST ETYPE)
      (setvar "MODEMACRO" "010 Architec")
      (setvar "CMDECHO" 0)
      (command "UNDO" "BE")
      (setq SS (ssget))
      (setq SSL1 (sslength SS))
      (setq N 0)
        (while (< N SSL1)
            (setq ENAME (ssname SS N)           
                  ELIST (entget ENAME)          
                  ETYPE (cdr (assoc 0 ELIST)))
            (cond
              ((= ETYPE "HATCH")
              (command "-HATCHEDIT" ENAME "DI" )
              )
            )
          (setq N (+ N 1))
        )
      (command "UNDO" "END")
      (setvar "CMDECHO" 1)
      (princ)
    )
