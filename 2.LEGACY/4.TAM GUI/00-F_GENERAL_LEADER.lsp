(vl-load-com)
(setvar "MODEMACRO" "010 Architect")
(defun c:A3 (/ occho lstss lstle lsttext p1 o1 dt lst1 lst botoadox toadox1 toadodiem1 lst2 
			lts3 pt1 xdau pt pdat textObj cle alignmentPoint)
(setvar "MODEMACRO" "010 Architect")
(setvar "CMDECHO" 0)
(setq occho (getvar "osmode"))  
(setq lstss (CV:ss-to-list (ssget (list (cons 0 "LEADER,*TEXT"))) nil))
(setq lstle (vl-remove-if-not '(lambda (x) (= (cdr (assoc 0 (entget x))) "LEADER")) lstss))
(setq lsttext (vl-remove-if-not '(lambda (x) (/= (cdr (assoc 0 (entget x))) "LEADER")) lstss))
(setq p1 (getpoint "\nChon diem cuoi leader."))
(setvar "osmode" 0)
(setq cle "T")
(foreach ent lstle
  (setq o1 (entget ent))
  (setq dt (cdr(assoc 0 o1)))
	(setq xdau (car (cdr (assoc 10 o1))))
    (setq lst1 (reverse o1))
    (setq lst (assoc 10 lst1))
    (setq botoadox (cdr(cdr lst)))
    (setq toadox1 (car p1))
    (setq toadodiem1 (append (list toadox1) botoadox))
    (setq lst2 (subst (cons 10 toadodiem1) lst lst1))
    (setq lts3 (reverse lst2))
    (entmod lts3)
	(if (> xdau toadox1)
	(setq cle "T")
	(setq cle "P")
	)
)
(foreach ent lsttext
  (setq o1 (entget ent))
  (setq dt (cdr(assoc 0 o1)))
(cond
    ((= dt "TEXT")
	(setq pt1 (cdr (assoc 10 o1)))
	(setq textObj (vlax-ename->vla-object ent))
	(setq pdat (append (list (car p1)) (cdr pt1)))
	(setq alignmentPoint (vlax-3d-point pdat))
    (if (= cle "T")
	(progn
	(vla-put-Alignment textObj acAlignmentLeft)
	(setq pt (vlax-variant-value (vla-get-InsertionPoint textObj)))
	(vla-move textObj pt alignmentPoint)
	)
	(progn
	(vla-put-Alignment textObj acAlignmentRight)
	(vla-put-TextAlignmentPoint textObj alignmentPoint)
	)
	)
    )
    ((= dt "MTEXT")   
    (setq pt1 (cdr (assoc 10 o1)))
	(setq textObj (vlax-ename->vla-object ent))
	(setq pdat (append (list (car p1)) (cdr pt1)))
	(setq alignmentPoint (vlax-3d-point pdat))
	(if (= cle "T")
	(progn
	(vla-put-AttachmentPoint textObj 7)
	(setq pt (vlax-variant-value (vla-get-InsertionPoint textObj)))
	(vla-move textObj pt alignmentPoint)
	)
	(progn 
	(vla-put-AttachmentPoint textObj 9)
	(setq pt (vlax-variant-value (vla-get-InsertionPoint textObj)))
	(vla-move textObj pt alignmentPoint)
	)
	)
    ) 
)
)
(setvar "osmode" occho)
(princ)
)
(defun CV:ss-to-list (ss vla / n e l)
(if ss
(progn
(setq n (sslength ss))
(while (setq e (ssname ss (setq n (1- n))))
(setq l (cons (if vla (vlax-ename->vla-object e) e) l))
)
)
)
)
