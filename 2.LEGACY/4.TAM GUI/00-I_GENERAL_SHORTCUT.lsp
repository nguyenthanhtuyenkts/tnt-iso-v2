;;; AUTOLISP TNT
;;; APPLOAD
;;; NO FIX
;;; GOI LENH TRONG COMMAND:
  ;; "-LENH": GOI LENH KHONG DUNG HOP THOAI
  ;; "_LENH": GOI LENH TIENG ANH ENGLISH
  ;; ".LENH": GOI LENH GOC NGUYEN THUY
  ;; "'ENH": GOI LENH KHI DANG DUNG LENH KHAC
  ;; "LENH": GOI LENH BINH THUONG TUY CAD
  ;; SAU "C:" LÀ LỆNH TẮT, TRONG COMMAND
;; 2. TRA MA DXF CUA DOI TUONG
    (defun c:DXF (/ MA MA1 )
    (setq MA (car (entsel)))
    (setq MA1 (entget MA))
    (princ MA1)
    (princ))
;;; PHIM TAT TNT
(vl-load-com)
(setvar "MODEMACRO" "010 Architect")
 ;; 1.PHIM TAT LENH VE
    (defun c:SE1 ()                       ; BẬT LẠI ALL BẮT ĐIỂM
      (command "OSMODE" 16383)(princ))
    (defun c:ATT ()                       ; SỬA BLOCK ATT NHANH
      (command ".ATTIPEDIT")(princ))
    (defun c:wq ()                        ; VẼ NÉT WIPEOUT
      (command ".WIPEOUT")(princ))
    (defun c:BB ()                        ; TẠO NÉT BO KÍN
      (command ".BOUNDARY")(princ))
 ;; 2.LENH COPY
    (defun c:C (/ A B)
      (setq A (ssget))
      (setq B (getpoint "\n SELECT POINT:"))
      (command "COPY" A "" "M" B )(princ))
    (defun c:CV (/ A B)                   ; COPY ĐỐI TƯỢNG NHƯNG CÓ ĐIỂM BASE
      (setq A (ssget))
      (setq B (getpoint "\n SELECT BASE POINT:"))
      (command ".COPYBASE" B A "")(princ))
    (defun c:CB ()                        ; DÁN VÀO ĐIỂM BASE
        (command ".PASTEBLOCK")(princ))
  ;; 3.LENH CHINH SUA
    (defun c:BR (/ A B)                   ; CHIA ĐỐI TƯỢNG
      (setq A (ssget))
      (setq B (getpoint "\n SELECT POINT:"))
      (command ".BREAK" A B B )(princ))    
    (defun c:CC ()
      (command ".CIRCLE")(princ))
    (defun c:E1 ()
      (command ".EXTEND")(princ))
    (defun c:` ()
      (command ".LINE")(princ))
    (defun c:`` ()
      (command ".PLINE")(princ))
    (defun c:V ()
      (command ".MOVE")(princ))
    (defun c:Q ()
      (command ".MATCHPROP")(princ))
    (defun c:R ()
      (command ".RECTANG")(princ))
    (defun c:TT ()
      (command ".TRIM")(princ))    
    (defun c:SF ()
      (command ".OFFSET")(princ))
    (defun c:FF ()
      (command ".MIRROR")(princ))    
    (defun c:``` ()
      (command ".SPLINE")(princ))
    (defun c:REF ()
      (command "-REFEDIT" "O" "A" "Y")(princ))
    (defun c:REFC ()
      (command ".REFCLOSE" "S" "")(princ))
    (defun c:BE ()
      (command "-BEDIT")(princ))
    (defun c:BC ()
      (command "_BCLOSE" "")(princ))
    (defun c:XZ ()
      (command ".XLINE")(princ))
    (defun c:1` ()    
      (command ".XLINE" "V" )(princ))
    (defun c:2` ()
      (COMMAND ".XLINE" "H" )(princ))
    (defun c:F ()
      (command ".FILLET") (princ))
    (defun c:F1 ()
      (command ".AECFILLET") (princ))
    (defun c:DRF (/ A)
      (SETQ A (SSGET))
      (command ".DRAWORDER" A "" "F" ) (princ))
    (defun c:DRB (/ A)
      (SETQ A (SSGET))
      (command ".DRAWORDER" A "" "B" ) (princ))
    (defun c:xre ()
      (command "-XREF" "R" "*" ) (princ))
 ;; 4.PHIM TAT VE SELECT
    (defun c:SD ()
      (sssetfirst nil (ssget (list (cons 0 "DIMENSION"))))
      (princ))
    (defun c:SA ()
      (sssetfirst nil (ssget (list (cons 0 "LEADER"))))
      (princ))
    (defun c:SB ()
      (sssetfirst nil (ssget (list (cons 0 "INSERT"))))
      (princ))
    (defun c:ST ()
      (sssetfirst nil (ssget (list (cons 0 "*TEXT,LEADER"))))  
      (princ))
    (defun c:SHT ()
      (sssetfirst nil (ssget (list (cons 0 "HATCH"))))
      (princ))
    (defun c:SV ()
      (sssetfirst nil (ssget (list (cons 0 "VIEWPORT"))))
      (princ)) 
 ;; 5.PHIM TAT VE DIM
    (defun c:D ()
         (command ".DIMLINEAR")   
         (PRINC))
    (defun c:DA ()
         (command ".DIMALIGNED")
         (PRINC))
    (defun c:DN ()
         (command ".DIMANGULAR")
         (PRINC))
    (defun c:DG ()
         (command ".DIMRADIUS")
         (PRINC))
    (defun c:DC ()
         (command ".DIMCONTINUE")          
         (PRINC))
    (defun c:DS ()         
         (command "DIMSETINSERT")  
         (PRINC))      
    (defun c:DB (/ A)
         (SETQ A (SSGET))
         (command "DIMSETMOVE" A)   
         (PRINC))
    (defun c:DE ()        
         (command "DIMSETDELETE")  
         (PRINC))
    (defun c:DX (/ A)  
         (SETQ A (SSGET))  
         (command "DIMSETEXTEND" A "E" )  
         (PRINC))
    (defun c:D1 (/ A B)
    (setq A (getint "\n NHẬP TỶ LỆ: "))
    (if (/= A 0)
        (progn
            (setq B (/ 1.0 A))
            (command ".DIMLFAC" B)
        )
        (princ "\nLỗi: TỶ LỆ không thể bằng 0.")
    )
    (princ)
    )
    (defun c:D2 ()
         (command ".DIMSCALE")
         (PRINC))
 ;; 6.PHIM TAT VE LAYER
    (defun c:QQ ()
      (command ".LAYMCUR")
      (PRINC))
    (defun c:1 ()
      (setvar "CMDECHO" 0)
      (setvar "DIMLAYER" ".")    
      (command ".LAYISO")
      (setvar "CMDECHO" 1)
    (PRINC))
    (defun c:2 ()
    (command ".LAYOFF")
    (PRINC))
    (defun c:3 ()
      (setvar "CMDECHO" 0)
      (setvar "DIMLAYER" "...11_TNT_LINE_DIMENSION" )
      (command "-LAYER" "ON" "*" "")
      (setvar "CMDECHO" 1)
      (PRINC))      
 ;; 7.PHIM TAT VE LAYOUT
    (defun c:V1 ()
      (command "_-vports" "_2" "V")
      (PRINC))
    (defun c:V2 ()
      (command "_-vports" "_2" "H")
      (PRINC))
    (defun c:V3 ()
      (command "_-vports" "_SI" )
      (PRINC))
    (defun c:C1 ( / TILE)
    (setq TILE (getvar "TILEMODE")) 
    (if (= TILE 0)
        (progn
            (setvar "TILEMODE" 1))      
        (progn
            (setvar "TILEMODE" 0))
    )
    (princ))
    (defun c:C3 ()
      (command ".MODEL")
      (PRINC))
    (defun c:C2 ()
      (command ".LAYOUT" "S" "" )
      (PRINC))
 ;; 8.PHIM TAT VE GROUP 
    (defun c:g1 ()
      (if (= (getvar "PICKSTYLE") 0)
          (setvar "PICKSTYLE" 1)
          (setvar "PICKSTYLE" 0)
      )
      (princ))
 ;; 9.PHIM TAT CHUNG
    (defun C:PU ()
        (setvar "CMDECHO" 0)
        (command "-PURGE" "ALL" "" "N" )
        (command "-PURGE" "R" "" "N" )
        (command ".AUDIT" "Y" )
          (setvar "CMDECHO" 1)
        (princ)
      )
;; 10. PHIM TAT TEXT  
;; 11. PHIM TAT BLOCK
;; 12. PHIM TAT XOAY
  (defun c:RT ()
      (command ".ROTATE")(princ)) 
  ;;;XOAY NHANH 90
  (defun QR (rot / ss minpt maxpt eLL eUR LL UR)
    (if (setq ss (ssget "_:L"))
      (progn
        (repeat (setq n (sslength ss))
          (vla-getboundingbox (vlax-ename->vla-object (ssname ss (setq n (1- n)))) 'minpt 'maxpt)
          (setq
            eLL (vlax-safearray->list minpt)
            eUR (vlax-safearray->list maxpt)
            LL (if LL (mapcar 'min eLL LL) eLL)
            UR (if UR (mapcar 'max eUR UR) eUR)
          )
        )
        (command "_.rotate" ss "" "_none" (trans (mapcar '/ (mapcar '+ LL UR) '(2 2 2)) 0 1) rot)
      )
    )
    (princ)
  )
  (defun C:RT1 () (QR "90"))
  (defun C:RT2 () (QR "-90"))
  ;(defun C:RT3 () (QR "45"))
  ;(defun C:RT4 () (QR "-45"))
  ;;;XOAY TEXT VA BLOK VE 0 NHANH
  (defun c:RR (/ ang ss name)
  (vl-load-com)
  (setq ang (atan (cadr (trans (getvar 'UCSXDIR) 0 (trans '(0. 0. 1.) 1 0 T) T)) (car (trans (getvar 'UCSXDIR) 0 (trans '(0. 0. 1.) 1 0 T) T))))
  (if (ssget "_:L" '((0 . "INSERT,MTEXT,MULTILEADER,TEXT")))
    (progn
      (vlax-for x (vla-get-activeselectionset (vla-get-activedocument (vlax-get-acad-object)))
        (cond ((vl-position (setq name (vla-get-objectname x)) '("AcDbBlockReference" "AcDbText")) (vla-put-rotation x ang))
              ((eq name "AcDbMText") (vla-put-rotation x 0.))
              ((and (eq name "AcDbMLeader") (eq (vla-get-contenttype x) 2)) (vla-put-textrotation x 0.))))
      (vla-delete ss)
    )
  )
  (princ)
  )
  ;;;XOAY RANDOM
  (defun c:RRT (/ ss num x ang ename elist pnt)
  (command "UNDO" "GROUP")
  (setq ss (ssget "_I"))
  (if (not ss) (setq ss (ssget)))
  (if ss
    (progn
      (setq num (sslength ss))
      (setq x 0)
      (repeat num
        (setq ang (* 180 (LM:rand)))
        (setq ename (ssname ss x))
        (setq elist (entget ename))
        (setq pnt (cdr(assoc 10 elist)))
        (command "Rotate" ename "" pnt ang)
        (setq x (1+ x))
      )
    )
  )
  (command "UNDO" "END")
  (princ)
  )
  (defun LM:rand (/ a c m)
    (setq m 4294967296.0
          a 1664525.0
          c 1013904223.0
          $xn (rem (+ c (* a (cond ($xn) ((getvar 'date))))) m))
    (/ $xn m)
  )
