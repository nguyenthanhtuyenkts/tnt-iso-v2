;;; Isolated runtime fixture. Run in a NEW throwaway drawing only.
(vl-load-com)
(load "D:/0.TNT ISO 2026/00.RELEASE 14/TNT_SUPPORT_LISP/TNT_EXPORT_ACAD2014.lsp")
(setq exp14:dir "D:/0.TNT ISO 2026/1.WORK/ACAD2014_TEST/")
(setq exp14:log (open (strcat exp14:dir "export2014_result.txt") "w"))
(defun exp14:check (name pass)
  (write-line (strcat name ": " (if pass "PASS" "FAIL")) exp14:log)
  (princ (strcat "\n" name ": " (if pass "PASS" "FAIL"))))
(defun exp14:snapshot (/ block obj result)
  (vlax-for block (vla-get-Blocks exp14:doc)
    (vlax-for obj block
      (setq result (cons (entget (vlax-vla-object->ename obj) '("*")) result))))
  result)
(setq exp14:doc (vla-get-ActiveDocument (vlax-get-acad-object))
      exp14:ms (vla-get-ModelSpace exp14:doc)
      exp14:ps (vla-get-PaperSpace exp14:doc))
(write-line (strcat "ACADVER=" (getvar "ACADVER")) exp14:log)
(setq exp14:line (vla-AddLine exp14:ms (vlax-3d-point '(100 200 0)) (vlax-3d-point '(150 200 0))))
(vla-put-Color exp14:line 3)
(setq exp14:text (vla-AddText exp14:ms "UNSAVED TEXT" (vlax-3d-point '(110 210 0)) 3))
(vla-AddText exp14:ps "LAYOUT CONTENT" (vlax-3d-point '(10 10 0)) 3)
(setq exp14:blk (vla-Add (vla-get-Blocks exp14:doc) (vlax-3d-point '(0 0 0)) "EXPORT_NESTED"))
(vla-AddText exp14:blk "NESTED CONTENT" (vlax-3d-point '(0 0 0)) 2)
(setq exp14:br (vla-InsertBlock exp14:ms (vlax-3d-point '(300 400 0)) "EXPORT_NESTED" 1 1 1 0))
(setq exp14:before (exp14:snapshot)
      exp14:dbmod (getvar "DBMOD")
      exp14:fullname (vla-get-FullName exp14:doc)
      exp14:pref (vla-get-OpenSave (vla-get-Preferences (vlax-get-acad-object)))
      exp14:type (vla-get-SaveAsType exp14:pref)
      exp14:filedia (getvar "FILEDIA")
      exp14:echo (getvar "CMDECHO"))
(setq exp14:ss (ssadd))
(ssadd (vlax-vla-object->ename exp14:line) exp14:ss)
(ssadd (vlax-vla-object->ename exp14:br) exp14:ss)
(setq exp14:selected (vl-filename-mktemp "selected_" exp14:dir ".dwg"))
(if (findfile exp14:selected) (vl-file-delete exp14:selected))
(exp14:check "SELECTED_EXPORT" (TNT:EXP14:WRITE exp14:selected exp14:ss))
(exp14:check "SELECTED_AC1027" (= (TNT:EXP14:HEADER exp14:selected) "AC1027"))
(exp14:check "SELECTED_SOURCE_ENTITIES_UNCHANGED" (equal exp14:before (exp14:snapshot)))
(exp14:check "SELECTED_SOURCE_DBMOD_UNCHANGED" (= exp14:dbmod (getvar "DBMOD")))
(setq exp14:whole (vl-filename-mktemp "whole_" exp14:dir ".dwg"))
(if (findfile exp14:whole) (vl-file-delete exp14:whole))
(exp14:check "WHOLE_EXPORT" (TNT:EXP14:WRITE exp14:whole nil))
(exp14:check "WHOLE_AC1027" (= (TNT:EXP14:HEADER exp14:whole) "AC1027"))
(exp14:check "WHOLE_SOURCE_ENTITIES_UNCHANGED" (equal exp14:before (exp14:snapshot)))
(exp14:check "WHOLE_SOURCE_DBMOD_UNCHANGED" (= exp14:dbmod (getvar "DBMOD")))
(exp14:check "SOURCE_NAME_UNCHANGED" (= exp14:fullname (vla-get-FullName exp14:doc)))
(exp14:check "PREFERENCES_RESTORED" (= exp14:type (vla-get-SaveAsType exp14:pref)))
(exp14:check "VARIABLES_RESTORED" (and (= exp14:filedia (getvar "FILEDIA")) (= exp14:echo (getvar "CMDECHO"))))
(exp14:check "DEFAULT_SUFFIX" (wcmatch (TNT:EXP14:DEFAULT-PATH) "*_ACAD2014.dwg"))
(setq exp14:dbx (vla-GetInterfaceObject (vlax-get-acad-object) "ObjectDBX.AxDbDocument.19"))
(vla-Open exp14:dbx exp14:selected)
(exp14:check "REOPEN_SELECTED_MODEL_COUNT" (= (vla-get-Count (vla-get-ModelSpace exp14:dbx)) 2))
(setq exp14:gotline nil exp14:gotblock nil)
(vlax-for exp14:obj (vla-get-ModelSpace exp14:dbx)
  (cond
    ((= (vla-get-ObjectName exp14:obj) "AcDbLine")
      (setq exp14:gotline (and (= (vla-get-Color exp14:obj) 3)
        (equal (vlax-safearray->list (vlax-variant-value (vla-get-StartPoint exp14:obj))) '(100.0 200.0 0.0) 1e-8))))
    ((= (vla-get-ObjectName exp14:obj) "AcDbBlockReference")
      (setq exp14:gotblock (= (vla-get-Name exp14:obj) "EXPORT_NESTED")))))
(exp14:check "REOPEN_SELECTED_COORDINATES_COLOR_BLOCK" (and exp14:gotline exp14:gotblock))
(vlax-release-object exp14:dbx)
(setq exp14:dbx (vla-GetInterfaceObject (vlax-get-acad-object) "ObjectDBX.AxDbDocument.19"))
(vla-Open exp14:dbx exp14:whole)
(exp14:check "REOPEN_WHOLE_MODEL_COUNT" (= (vla-get-Count (vla-get-ModelSpace exp14:dbx)) 3))
(setq exp14:gotlayout nil exp14:gotunsaved nil)
(vlax-for exp14:obj (vla-get-ModelSpace exp14:dbx)
  (if (and (= (vla-get-ObjectName exp14:obj) "AcDbText") (= (vla-get-TextString exp14:obj) "UNSAVED TEXT"))
    (setq exp14:gotunsaved T)))
(vlax-for exp14:obj (vla-get-PaperSpace exp14:dbx)
  (if (and (= (vla-get-ObjectName exp14:obj) "AcDbText") (= (vla-get-TextString exp14:obj) "LAYOUT CONTENT"))
    (setq exp14:gotlayout T)))
(exp14:check "REOPEN_WHOLE_UNSAVED_CONTENT_AND_LAYOUT" (and exp14:gotunsaved exp14:gotlayout))
(vlax-release-object exp14:dbx)
(write-line (strcat "SELECTED_FILE=" exp14:selected) exp14:log)
(write-line (strcat "WHOLE_FILE=" exp14:whole) exp14:log)
(close exp14:log)
(princ)
