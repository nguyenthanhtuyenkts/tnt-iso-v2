(setq tnt14:out (open "D:/0.TNT ISO 2026/1.WORK/ACAD2014_TEST/result.txt" "w"))
(write-line (strcat "ACADVER=" (getvar "ACADVER")) tnt14:out)
(setq tnt14:r (vl-catch-all-apply 'load (list "D:/0.TNT ISO 2026/00.RELEASE 14/TNT_PACKAGE_00_SYSTEM_ALL.lsp")))
(write-line (strcat "TNT_PACKAGE_00_SYSTEM_ALL.lsp: " (if (vl-catch-all-error-p tnt14:r) (vl-catch-all-error-message tnt14:r) "OK")) tnt14:out)
(setq tnt14:r (vl-catch-all-apply 'load (list "D:/0.TNT ISO 2026/00.RELEASE 14/TNT_PACKAGE_01_CREATE_ALL.lsp")))
(write-line (strcat "TNT_PACKAGE_01_CREATE_ALL.lsp: " (if (vl-catch-all-error-p tnt14:r) (vl-catch-all-error-message tnt14:r) "OK")) tnt14:out)
(setq tnt14:r (vl-catch-all-apply 'load (list "D:/0.TNT ISO 2026/00.RELEASE 14/TNT_PACKAGE_02_GENERAL_ALL.lsp")))
(write-line (strcat "TNT_PACKAGE_02_GENERAL_ALL.lsp: " (if (vl-catch-all-error-p tnt14:r) (vl-catch-all-error-message tnt14:r) "OK")) tnt14:out)
(setq tnt14:r (vl-catch-all-apply 'load (list "D:/0.TNT ISO 2026/00.RELEASE 14/TNT_PACKAGE_03_MANAGE_ALL.lsp")))
(write-line (strcat "TNT_PACKAGE_03_MANAGE_ALL.lsp: " (if (vl-catch-all-error-p tnt14:r) (vl-catch-all-error-message tnt14:r) "OK")) tnt14:out)
(setq tnt14:r (vl-catch-all-apply 'load (list "D:/0.TNT ISO 2026/00.RELEASE 14/TNT_PACKAGE_04_DRAW_ALL.lsp")))
(write-line (strcat "TNT_PACKAGE_04_DRAW_ALL.lsp: " (if (vl-catch-all-error-p tnt14:r) (vl-catch-all-error-message tnt14:r) "OK")) tnt14:out)
(setq tnt14:r (vl-catch-all-apply 'load (list "D:/0.TNT ISO 2026/00.RELEASE 14/TNT_PACKAGE_05_LAYER_ALL.lsp")))
(write-line (strcat "TNT_PACKAGE_05_LAYER_ALL.lsp: " (if (vl-catch-all-error-p tnt14:r) (vl-catch-all-error-message tnt14:r) "OK")) tnt14:out)
(setq tnt14:r (vl-catch-all-apply 'load (list "D:/0.TNT ISO 2026/00.RELEASE 14/TNT_PACKAGE_06_TEXT_ALL.lsp")))
(write-line (strcat "TNT_PACKAGE_06_TEXT_ALL.lsp: " (if (vl-catch-all-error-p tnt14:r) (vl-catch-all-error-message tnt14:r) "OK")) tnt14:out)
(setq tnt14:r (vl-catch-all-apply 'load (list "D:/0.TNT ISO 2026/00.RELEASE 14/TNT_PACKAGE_07_LEADER_ALL.lsp")))
(write-line (strcat "TNT_PACKAGE_07_LEADER_ALL.lsp: " (if (vl-catch-all-error-p tnt14:r) (vl-catch-all-error-message tnt14:r) "OK")) tnt14:out)
(setq tnt14:r (vl-catch-all-apply 'load (list "D:/0.TNT ISO 2026/00.RELEASE 14/TNT_PACKAGE_08_DIMENSION_ALL.lsp")))
(write-line (strcat "TNT_PACKAGE_08_DIMENSION_ALL.lsp: " (if (vl-catch-all-error-p tnt14:r) (vl-catch-all-error-message tnt14:r) "OK")) tnt14:out)
(setq tnt14:r (vl-catch-all-apply 'load (list "D:/0.TNT ISO 2026/00.RELEASE 14/TNT_PACKAGE_09_HATCH_ALL.lsp")))
(write-line (strcat "TNT_PACKAGE_09_HATCH_ALL.lsp: " (if (vl-catch-all-error-p tnt14:r) (vl-catch-all-error-message tnt14:r) "OK")) tnt14:out)
(setq tnt14:r (vl-catch-all-apply 'load (list "D:/0.TNT ISO 2026/00.RELEASE 14/TNT_PACKAGE_10_BLOCK_ALL.lsp")))
(write-line (strcat "TNT_PACKAGE_10_BLOCK_ALL.lsp: " (if (vl-catch-all-error-p tnt14:r) (vl-catch-all-error-message tnt14:r) "OK")) tnt14:out)
(setq tnt14:r (vl-catch-all-apply 'load (list "D:/0.TNT ISO 2026/00.RELEASE 14/TNT_PACKAGE_11_SHORTCUT.lsp")))
(write-line (strcat "TNT_PACKAGE_11_SHORTCUT.lsp: " (if (vl-catch-all-error-p tnt14:r) (vl-catch-all-error-message tnt14:r) "OK")) tnt14:out)
(setq tnt14:r (vl-catch-all-apply 'load (list "D:/0.TNT ISO 2026/00.RELEASE 14/TNT_SUPPORT_LISP/TNT_AEC_DOWN2014.lsp")))
(write-line (strcat "TNT_AEC_DOWN2014.lsp: " (if (vl-catch-all-error-p tnt14:r) (vl-catch-all-error-message tnt14:r) "OK")) tnt14:out)
(setq tnt14:r (vl-catch-all-apply 'load (list "D:/0.TNT ISO 2026/00.RELEASE 14/TNT_SUPPORT_LISP/TNT_AEC_TO_ACAD.lsp")))
(write-line (strcat "TNT_AEC_TO_ACAD.lsp: " (if (vl-catch-all-error-p tnt14:r) (vl-catch-all-error-message tnt14:r) "OK")) tnt14:out)
(setq tnt14:r (vl-catch-all-apply 'load (list "D:/0.TNT ISO 2026/00.RELEASE 14/TNT_SUPPORT_LISP/TNT_BACKUP.lsp")))
(write-line (strcat "TNT_BACKUP.lsp: " (if (vl-catch-all-error-p tnt14:r) (vl-catch-all-error-message tnt14:r) "OK")) tnt14:out)
(setq tnt14:r (vl-catch-all-apply 'load (list "D:/0.TNT ISO 2026/00.RELEASE 14/TNT_SUPPORT_LISP/TNT_LAYER_LISTING.lsp")))
(write-line (strcat "TNT_LAYER_LISTING.lsp: " (if (vl-catch-all-error-p tnt14:r) (vl-catch-all-error-message tnt14:r) "OK")) tnt14:out)
(setq tnt14:r (vl-catch-all-apply 'load (list "D:/0.TNT ISO 2026/00.RELEASE 14/TNT_SUPPORT_LISP/TNT_LAYER_SYNC_ALL.lsp")))
(write-line (strcat "TNT_LAYER_SYNC_ALL.lsp: " (if (vl-catch-all-error-p tnt14:r) (vl-catch-all-error-message tnt14:r) "OK")) tnt14:out)
(setq tnt14:r (vl-catch-all-apply 'load (list "D:/0.TNT ISO 2026/00.RELEASE 14/TNT_SUPPORT_LISP/TNT_MEP_BASE.lsp")))
(write-line (strcat "TNT_MEP_BASE.lsp: " (if (vl-catch-all-error-p tnt14:r) (vl-catch-all-error-message tnt14:r) "OK")) tnt14:out)
(setq tnt14:r (vl-catch-all-apply 'load (list "D:/0.TNT ISO 2026/00.RELEASE 14/TNT_SUPPORT_LISP/TNT_MIGRATE_DIMSTYLE.lsp")))
(write-line (strcat "TNT_MIGRATE_DIMSTYLE.lsp: " (if (vl-catch-all-error-p tnt14:r) (vl-catch-all-error-message tnt14:r) "OK")) tnt14:out)
(setq tnt14:r (vl-catch-all-apply 'load (list "D:/0.TNT ISO 2026/00.RELEASE 14/TNT_SUPPORT_LISP/TNT_STT.lsp")))
(write-line (strcat "TNT_STT.lsp: " (if (vl-catch-all-error-p tnt14:r) (vl-catch-all-error-message tnt14:r) "OK")) tnt14:out)
(close tnt14:out)
(princ)
