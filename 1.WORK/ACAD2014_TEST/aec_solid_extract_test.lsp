(vl-load-com)
(load "D:/0.TNT ISO 2026/00.RELEASE 14/TNT_SUPPORT_LISP/TNT_AEC_TO_ACAD.lsp")
(setq out (open "D:/0.TNT ISO 2026/1.WORK/ACAD2014_TEST/aec_solid_extract_result.txt" "w"))
(defun check (label flag) (write-line (strcat label ": " (if flag "PASS" "FAIL")) out))
(setq doc (vla-get-ActiveDocument (vlax-get-acad-object)) ms (vla-get-ModelSpace doc))
(TNT:AEC:ENSURE-TARGET-LAYER)
(setq def (vla-Add (vla-get-Blocks doc) (vlax-3d-point '(5 7 0)) "TNT_SOLID_EXTRACT_INNER_TEST"))
(setq outer (vla-AddCircle def (vlax-3d-point '(8 9 0)) 2)
      inner (vla-AddCircle def (vlax-3d-point '(8 9 0)) 0.5)
      arr (vlax-make-safearray vlax-vbObject '(0 . 0))
      hatch (vla-AddHatch def 0 "SOLID" :vlax-true))
(vlax-safearray-put-element arr 0 outer)
(vla-AppendOuterLoop hatch arr)
(vlax-safearray-put-element arr 0 inner)
(vla-AppendInnerLoop hatch arr)
(vla-Evaluate hatch)
(setq sourceArea (vla-get-Area hatch) sourceEname (vlax-vla-object->ename hatch))
(setq color (vla-get-TrueColor hatch))
(vla-SetRGB color 180 20 70)
(vla-put-TrueColor hatch color)
(vlax-release-object color)
(setq h17 (vla-Copy hatch))
(TNT:AEC:FORCE-ACI h17 17)
(setq h17ename (vlax-vla-object->ename h17))
(setq d17 (TNT:AEC:DELETE-SOLID-17))
(check "DELETE_ONLY_SOLID_17" (and (null (entget h17ename)) (entget sourceEname)))
(check "NORMALIZE_TRUECOLOR_SOLID" (TNT:AEC:NORMALIZE-OBJECT hatch))
(check "SOLID_IS_ACI_251" (and (= (vla-get-Color hatch) 251) (null (assoc 420 (entget sourceEname)))))
(setq parent (vla-Add (vla-get-Blocks doc) (vlax-3d-point '(0 0 0)) "TNT_SOLID_EXTRACT_OUTER_TEST"))
(vla-InsertBlock parent (vlax-3d-point '(10 20 0)) "TNT_SOLID_EXTRACT_INNER_TEST" 2 3 1 (/ pi 2))
(vla-InsertBlock ms (vlax-3d-point '(100 200 0)) "TNT_SOLID_EXTRACT_OUTER_TEST" -1 2 1 0)
(vla-InsertBlock ms (vlax-3d-point '(300 100 0)) "TNT_SOLID_EXTRACT_OUTER_TEST" 1 1 1 0)
(setq extracted (TNT:AEC:EXTRACT-SOLIDS))
(check "EXTRACTION_NO_FAILURE" (= (cadr extracted) 0))
(check "SHARED_SOURCE_REMOVED" (null (entget sourceEname)))
(check "BOUNDARY_GEOMETRY_PRESERVED" (and (not (vlax-erased-p outer)) (not (vlax-erased-p inner))))
(setq found1 nil found2 nil)
(vlax-for obj ms
 (if (TNT:AEC:SOLID-HATCH-EXCEPTION-P obj)
  (progn
   (vla-GetBoundingBox obj 'lo 'hi)
   (setq center (mapcar '(lambda (a b) (/ (+ a b) 2.0)) (vlax-safearray->list lo) (vlax-safearray->list hi)))
   (if (equal center '(96.0 252.0 0.0) 1e-6) (setq found1 obj))
   (if (equal center '(304.0 126.0 0.0) 1e-6) (setq found2 obj)))))
(check "NESTED_MIRROR_BASEPOINT_POSITION" (and found1 found2))
(check "NONUNIFORM_AREA_AND_HOLES" (and found1 found2 (= (vla-get-NumberOfLoops found1) 2)
 (equal (vla-get-Area found1) (* sourceArea 12) 1e-5)
 (equal (vla-get-Area found2) (* sourceArea 6) 1e-5)))
(check "COPIES_ARE_INDEPENDENT_ACI_251" (and found1 found2
 (= (vla-get-AssociativeHatch found1) :vlax-false)
 (= (vla-get-AssociativeHatch found2) :vlax-false)
 (= (vla-get-Color found1) 251) (= (vla-get-Color found2) 251)))
(setq orderResult (TNT:AEC:SOLIDS-TO-TOP))
(check "DRAW_ORDER_NO_FAILURE" (= (cadr orderResult) 0))
(close out)
