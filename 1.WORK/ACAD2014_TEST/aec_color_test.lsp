(vl-load-com)
(load "D:/0.TNT ISO 2026/00.RELEASE 14/TNT_SUPPORT_LISP/TNT_AEC_TO_ACAD.lsp")
(setq out (open "D:/0.TNT ISO 2026/1.WORK/ACAD2014_TEST/aec_color_result.txt" "w"))
(defun check (label flag) (write-line (strcat label ": " (if flag "PASS" "FAIL")) out))
(setq doc (vla-get-ActiveDocument (vlax-get-acad-object)) ms (vla-get-ModelSpace doc))
(setq mt (vla-AddMText ms (vlax-3d-point '(0 0 0)) 100 "{\\C1;RED} {\\H2x;BIG}"))
(setq tx (vla-AddText ms "TEXT" (vlax-3d-point '(0 20 0)) 3))
(setq dm (vla-AddDimAligned ms (vlax-3d-point '(0 0 0)) (vlax-3d-point '(20 0 0)) (vlax-3d-point '(10 10 0))))
(vla-put-TextOverride dm "{\\C3;<>}")
(setq sty (vla-get-StyleName tx) lay (vla-get-Layer tx))
(setq blk (vla-Add (vla-get-Blocks doc) (vlax-3d-point '(0 0 0)) "AEC_TEXT_TEST"))
(setq bt (vla-AddText blk "BLOCK TEXT" (vlax-3d-point '(0 0 0)) 2))
(setq at (vla-AddAttribute blk 2 0 "Prompt" (vlax-3d-point '(0 3 0)) "TAG" "VALUE"))
(setq outer (vla-Add (vla-get-Blocks doc) (vlax-3d-point '(0 0 0)) "AEC_OUTER_TEST"))
(setq br (vla-InsertBlock outer (vlax-3d-point '(0 0 0)) "AEC_TEXT_TEST" 1 1 1 0))
(vla-InsertBlock ms (vlax-3d-point '(0 0 0)) "AEC_OUTER_TEST" 1 1 1 0)
(setq result (TNT:AEC:COLOR-ALL-TEXT))
(check "NO_ERRORS" (= (cadr result) 0))
(check "TEXT_COLOR_STYLE_LAYER" (and (= (vla-get-Color tx) 251) (= sty (vla-get-StyleName tx)) (= lay (vla-get-Layer tx))))
(check "MTEXT_COLOR_FORMAT" (and (= (vla-get-Color mt) 251) (= (vla-get-TextString mt) "{RED} {\\H2x;BIG}")))
(check "DIM_TEXT_ONLY" (and (= (vla-get-TextColor dm) 251) (= (vla-get-TextOverride dm) "{<>}")))
(check "NESTED_BLOCK_TEXT" (= (vla-get-Color bt) 251))
(check "ATTRIBUTE" (= (vla-get-Color (car (vlax-invoke br 'GetAttributes))) 251))
(check "ESCAPED_LITERAL" (= (TNT:AEC:STRIP-TEXT-COLORS "\\\\C1;literal") "\\\\C1;literal"))
(close out)
